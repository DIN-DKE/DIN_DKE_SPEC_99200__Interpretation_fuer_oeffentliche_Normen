# DIN VDE 0132 (VDE 0132):2018-07

# Specification: DIN VDE 0132 (VDE 0132):2018-07
- bib.al.original-language: en
- bib.dp.publication-date: 2018-07-01
- bib.tg.title-german: Brandbekämpfung und technische Hilfeleistung im Bereich elektrischer Anlagen
- bib.ts.document-type: undefined
- ids.document: 7104561
- obj.language: en
- pub.harmonization: IDiS ReqIF interpretation for public standards 1.3
- pub.sales-number: 0100473
- pub.software: VDE CaaS 0.1.6
- pub.supplier: VDE
- pub.transformation-date: 2026-08-04T08:38:18.689040748Z
- pub.url: https://[changeme].dke.de/api/publications/7104561/reqif

## pkn--7104561: Brandbekämpfung und technische Hilfeleistung im Bereich elektrischer Anlagen (document)
DIN VDE 0132 (VDE 0132):2018-07
- bib.al.original-language: en
- bib.dp.publication-date: 2018-07-01
- bib.ts.document-type: undefined
- ids.document: 7104561
- obj.language: de
- obj.specobject-type: document
- pub.harmonization: IDiS ReqIF interpretation for public standards 1.3
- pub.sales-number: 0100473
- pub.software: VDE CaaS 0.1.6
- pub.supplier: VDE
- pub.transformation-date: 2026-08-04T08:38:18.689040748Z
- pub.url: https://[changeme].dke.de/api/publications/7104561/reqif

## prov-7104561-216213ec54bd4b5 (heading)
- bib.al.original-language: en
- bib.dp.publication-date: 2018-07-01
- ids.document: 7104561
- ids.element: sub-titlepage.nat
- ids.language-synoptic: sub-titlepage.nat
- ids.tracing: hash-3973e022e93220f9212c18d0d0c543ae7c309e46640da93a4a0314de999f5112
- obj.element-name: heading
- obj.language: de
- obj.specobject-type: heading

### prov-7104561-d412308778cb459 (provision)
|  |  |  | DIN VDE 0132 (VDE 0132) |  |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 |  |  |
| --- | --- | --- | --- | --- | --- | --- | --- |
|  |  |  | Diese Norm ist zugleich eine VDE-Bestimmung im Sinne von VDE 0022. Sie ist nach Durchführung des vom VDE-Präsidium beschlossenen Genehmigungsverfahrens unter der oben angeführten Nummer in das VDE-Vorschriftenwerk aufgenommen und in der „etz Elektrotechnik + Automation“ bekannt gegeben worden. |  |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 |  |  |
| Vervielfältigung – auch für innerbetriebliche Zwecke – nicht gestattet. |  |  |  |  |  |  |  |
|  |  | ICS 13.220.10 |  | Ersatz für DIN VDE 0132 (VDE 0132):2015-10 Siehe Anwendungsbeginn |  |  |  |
|  | Brandbekämpfung und technische Hilfeleistung im Bereich elektrischer Anlagen Firefighting and technical assistance in or near electrical installations Lutte contre l’incendie et secours technique dans ou prés des installations électriques |  |  |  |  |  |  |
|  | Gesamtumfang 28 Seiten DKE Deutsche Kommission Elektrotechnik Elektronik Informationstechnik in DIN und VDE |  |  |  |  |  |  |
| © DIN Deutsches Institut für Normung e. V. und VDE Verband der Elektrotechnik Elektronik Informationstechnik e. V. Jede Art der Vervielfältigung, auch auszugsweise, nur mit Genehmigung des DIN, Berlin, und des VDE, Frankfurt am Main, gestattet. Einzelverkauf und Abonnements durch VDE VERLAG GMBH, 10625 Berlin Einzelverkauf auch durch Beuth Verlag GmbH, 10772 Berlin |  |  |  |  |  | Preisgr. 19 K VDE-Vertr.-Nr. 0100473 |  |
- bib.al.original-language: en
- bib.dp.publication-date: 2018-07-01
- ids.document: 7104561
- ids.element: sub-titlepage.nat
- ids.language-synoptic: sub-titlepage.nat
- ids.tracing: hash-18c5f7e458d7be8bcf1d9f32641d24e30ba7410198878ec77adcea0f530236d6
- obj.element-name: tabular-form
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

## prov-7104561-c5cab82e12d644e: Anwendungsbeginn (heading)
- bib.al.original-language: en
- bib.dp.publication-date: 2018-07-01
- ids.document: 7104561
- ids.element: section_Anwendungsbeginn
- ids.language-synoptic: section_Anwendungsbeginn
- ids.tracing: hash-1bdcf9ac8b1c21a70bd6cd3ee06cf196d38ba97645cca1c1a0e19d62e32c0b74
- obj.element-name: heading
- obj.language: de
- obj.specobject-type: heading

### tr--570aeb71-321d-47c4-82c1-10e363247405--y4UIIdoBqVS9: Anwendungsbeginn (provision)
Anwendungsbeginn dieser Norm ist 2018-07-01.
- bib.al.original-language: en
- bib.dp.publication-date: 2018-07-01
- ids.document: 7104561
- ids.element: section_Anwendungsbeginn
- ids.language-synoptic: section_Anwendungsbeginn
- ids.tracing: hash-d6ac43ddbfb4a864cf76ce30e18f0921d8d59a8bbe6e96581e59c37c7d98632b
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### tr--570aeb71-321d-47c4-82c1-10e363247405--7amxsAk4yVXO: Anwendungsbeginn (provision)
Für DIN VDE 0132 (VDE 0132):2015-10 besteht eine Übergangsfrist bis 2021-06-30.
- bib.al.original-language: en
- bib.dp.publication-date: 2018-07-01
- ids.document: 7104561
- ids.element: section_Anwendungsbeginn
- ids.language-synoptic: section_Anwendungsbeginn
- ids.tracing: hash-9721f9a268a99da63941d64619d4bb67ee877740bbe619fc7859204600d3a2cc
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

## prov-7104561-77cdac18e2be41f: Vorwort (heading)
- bib.al.original-language: en
- bib.dp.publication-date: 2018-07-01
- ids.document: 7104561
- ids.element: section_Vorwort
- ids.language-synoptic: section_Vorwort
- ids.tracing: hash-e7e70fbd91ff0408677cce896478868e83c8d72a0f873d6e01bd13c199b6841d
- obj.element-name: heading
- obj.language: de
- obj.specobject-type: heading

### tr--570aeb71-321d-47c4-82c1-10e363247405--w9BmklNJuYBp: Vorwort (provision)
Vorausgegangener Norm-Entwurf: E DIN VDE 0132 (VDE 0132):2017-04.
- bib.al.original-language: en
- bib.dp.publication-date: 2018-07-01
- ids.document: 7104561
- ids.element: section_Vorwort
- ids.language-synoptic: section_Vorwort
- ids.tracing: hash-b6ff58cf5255db062f634deef93c96a64a8a474ea0a17a8f610dad53408fdf24
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### tr--570aeb71-321d-47c4-82c1-10e363247405--QokBg1s5t0XA: Vorwort (provision)
Für diese Norm ist das nationale Arbeitsgremium K 213 „Brandbekämpfung in elektrischen Anlagen“ der DKE Deutsche Kommission Elektrotechnik Elektronik Informationstechnik in DIN und VDE (www.dke.de) zuständig.
- bib.al.original-language: en
- bib.dp.publication-date: 2018-07-01
- ids.document: 7104561
- ids.element: section_Vorwort
- ids.language-synoptic: section_Vorwort
- ids.tracing: hash-2346e4eb32225aec88ea80700a18c0df6997ee47f370b2bd6627093c7978d186
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### tr--570aeb71-321d-47c4-82c1-10e363247405--D411p1E5JyBy: Vorwort (provision)
Diese Norm regelt das Verhalten und die Verwendung von Geräten für die Brandbekämpfung und technische Hilfeleistung in elektrischen Anlagen und in deren Nähe.
- bib.al.original-language: en
- bib.dp.publication-date: 2018-07-01
- ids.document: 7104561
- ids.element: section_Vorwort
- ids.language-synoptic: section_Vorwort
- ids.tracing: hash-68da47c471bff1fcc039c0d1d59ba8f6ed1983e35cd853a74b67e8528de4b76c
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### tr--570aeb71-321d-47c4-82c1-10e363247405--jfPg2j5gisgl: Vorwort (provision)
Zudem kann diese Norm dem Anwender Hilfestellung bei der Erstellung der Gefährdungsbeurteilung nach der Betriebsicherheitsverordnung bzw. der DGUV Vorschrift 1 „Grundsätze der Prävention“ geben.
- bib.al.original-language: en
- bib.dp.publication-date: 2018-07-01
- ids.document: 7104561
- ids.element: section_Vorwort
- ids.language-synoptic: section_Vorwort
- ids.tracing: hash-b17a358f6c75a27a74e78ab8e66461e70f12f5284b6ab72c9f310233c8cae2b7
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### tr--570aeb71-321d-47c4-82c1-10e363247405--Zvps5hhZ3WT4: Vorwort (provision)
Es wird auf die Möglichkeit hingewiesen, dass einige Elemente dieses Dokuments Patentrechte berühren können.
- bib.al.original-language: en
- bib.dp.publication-date: 2018-07-01
- ids.document: 7104561
- ids.element: section_Vorwort
- ids.language-synoptic: section_Vorwort
- ids.tracing: hash-1ab87c64b1816babc26a2cf3a5a19a2e5c56d4a8017801545dfea335e06cf022
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### tr--570aeb71-321d-47c4-82c1-10e363247405--Cirt6cr5RhEv: Vorwort (provision)
DIN und DKE sind nicht dafür verantwortlich, einige oder alle diesbezüglichen Patentrechte zu identifizieren.
- bib.al.original-language: en
- bib.dp.publication-date: 2018-07-01
- ids.document: 7104561
- ids.element: section_Vorwort
- ids.language-synoptic: section_Vorwort
- ids.tracing: hash-d3c4225cea32d6f8f343bc4a69f42177dedd9a0cc29cf19aa532756bfac577a0
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-bd710bd3f14b461: Änderungen (heading)
- bib.al.original-language: en
- bib.dp.publication-date: 2018-07-01
- ids.document: 7104561
- ids.element: section_AEnderungen
- ids.language-synoptic: section_AEnderungen
- ids.tracing: hash-0c3e021cf6c69f85a4e9b6d0db067ce3a675683d4ab01e548827c6e2514b3e08
- obj.element-name: heading
- obj.language: de
- obj.specobject-type: heading

#### tr--570aeb71-321d-47c4-82c1-10e363247405--8e81SQwQ0H0l: Änderungen (provision)
Gegenüber DIN VDE 0132 (VDE 0132):2015-10 wurden folgende Änderungen vorgenommen:
- a)
a) 5.1.3 "Maßnahmen bei Überflutung zur Sicherstellung der Personensicherheit" redaktionell geändert;
- b)
b) 5.1.5 "Besondere Maßnahmen bei Lithium-Ionen-Akkumulatoren" neu aufgenommen.
- bib.al.original-language: en
- bib.dp.publication-date: 2018-07-01
- ids.document: 7104561
- ids.element: section_AEnderungen
- ids.language-synoptic: section_AEnderungen
- ids.tracing: hash-c53905c0cd708955a879212fc0c87fd104a30f925c7b1d69c97152cdefa72166
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-7104561-61233a5507d04b5
- cross-reference -> prov-7104561-de920128e095448

### prov-7104561-46046268cd5348e: Frühere Ausgaben (heading)
- bib.al.original-language: en
- bib.dp.publication-date: 2018-07-01
- ids.document: 7104561
- ids.element: section_Fruehere_Ausgaben
- ids.language-synoptic: section_Fruehere_Ausgaben
- ids.tracing: hash-75d05358c181edf8bca02f6313216e4437eb4db57dc1530db4cf8b33d17ebcb5
- obj.element-name: heading
- obj.language: de
- obj.specobject-type: heading

#### tr--570aeb71-321d-47c4-82c1-10e363247405--Xhzusw13mCPP: Frühere Ausgaben (provision)
DIN VDE 0132 (VDE 0132): 1979-02, 1989-11 , 2001-08 , 2008-08 , 2012-08 , 2015-10
- bib.al.original-language: en
- bib.dp.publication-date: 2018-07-01
- ids.document: 7104561
- ids.element: section_Fruehere_Ausgaben
- ids.language-synoptic: section_Fruehere_Ausgaben
- ids.tracing: hash-e9ba8679aeb384f67e014e4d24bbf4cf58e227931681cbe6ca20e7e85de0d632
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

## prov-7104561-d37a10991b7b488: Anwendungsbereich (heading)
- bib.al.original-language: en
- bib.dp.publication-date: 2018-07-01
- ids.document: 7104561
- ids.element: section_1
- ids.language-synoptic: section_1
- ids.tracing: hash-a63f7d5a3ffbf91950d89662d586dec802464fe40c8e3ef99dd0f3ea98b61b73
- obj.clause-number: 1
- obj.element-name: heading
- obj.language: de
- obj.specobject-type: heading
- ChapterName: 1 Anwendungsbereich

### tr--570aeb71-321d-47c4-82c1-10e363247405--4S21T4padr3O: Anwendungsbereich (provision)
Diese Norm dient zur Unterrichtung der Personen, die für die Brandbekämpfung und technische Hilfeleistung in elektrischen Anlagen und in deren Nähe zuständig sind.
- bib.al.original-language: en
- bib.dp.publication-date: 2018-07-01
- ids.document: 7104561
- ids.element: section_1
- ids.language-synoptic: section_1
- ids.tracing: hash-ce50735272363708441d1f2df4c767c774080c46f6a48852a4c31d6bcdb32d8f
- obj.clause-number: 1
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### tr--570aeb71-321d-47c4-82c1-10e363247405--LwO39kNJVVfs: Anwendungsbereich (provision)
Die in dieser Norm angegebenen Werte der Mindestabstände für Annäherung und Löschmitteleinsatz gelten nicht für Anlagen mit Nennspannungen bis AC 50 V (Wechselspannung) / DC 120 V (Gleichspannung).
- bib.al.original-language: en
- bib.dp.publication-date: 2018-07-01
- ids.document: 7104561
- ids.element: section_1
- ids.language-synoptic: section_1
- ids.tracing: hash-a39c2f346027ca6b42a234d54a988556cf461077ca63f44b28a8d53c09e9c688
- obj.clause-number: 1
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### tr--570aeb71-321d-47c4-82c1-10e363247405--Ybl9FXyWiyBl: Anwendungsbereich (provision)
Die Norm gilt nicht für die Errichtung und den Betrieb ortsfester Löschanlagen, für Beregnungsanlagen, Wasserwerfer und dergleichen sowie für besondere Löschmaßnahmen, wie z. B. das Fluten von Kabelkanälen mit Wasser oder Schaum.
- bib.al.original-language: en
- bib.dp.publication-date: 2018-07-01
- ids.document: 7104561
- ids.element: section_1
- ids.language-synoptic: section_1
- ids.tracing: hash-2d91564da5f71cd2dd511c537352e01b2e20068a84c56fd25d5eabf5d725a57c
- obj.clause-number: 1
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### tr--570aeb71-321d-47c4-82c1-10e363247405--qkxdSf9PvUCQ: Anwendungsbereich (provision)
Diese Norm gilt auch für die Verwendung von Strahlrohren nach DIN 14365-1:1991-02 und DIN 14365-2:1986-09, die nicht europäisch genormt sind, sofern diese noch im Einsatz sind.
- bib.al.original-language: en
- bib.dp.publication-date: 2018-07-01
- ids.document: 7104561
- ids.element: section_1
- ids.language-synoptic: section_1
- ids.tracing: hash-0e4d5d17401b83d91784c766d9c641d098edfd36b4b50b563fc0d5ab7a575290
- obj.clause-number: 1
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

## prov-7104561-f14c89919df14bc: Normative Verweisungen (heading)
- bib.al.original-language: en
- bib.dp.publication-date: 2018-07-01
- ids.document: 7104561
- ids.element: section_2
- ids.language-synoptic: section_2
- ids.tracing: hash-18be8f0842e19da340e69abb27d0e5939d8a7d18b7373f77a2954f8853797954
- obj.clause-number: 2
- obj.element-name: heading
- obj.language: de
- obj.specobject-type: heading
- ChapterName: 2 Normative Verweisungen

### tr--570aeb71-321d-47c4-82c1-10e363247405--6NbORhGBBxcR: Normative Verweisungen (provision)
Die folgenden Dokumente, die in diesem Dokument teilweise oder als Ganzes zitiert werden, sind für die Anwendung dieses Dokuments erforderlich.
- bib.al.original-language: en
- bib.dp.publication-date: 2018-07-01
- ids.document: 7104561
- ids.element: section_2
- ids.language-synoptic: section_2
- ids.tracing: hash-19ac98809402cc9d36bbec92e184996209a61abf4b32a1a87220f8f8a849dcff
- obj.clause-number: 2
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### tr--570aeb71-321d-47c4-82c1-10e363247405--Nc7VoCTfnbWc: Normative Verweisungen (provision)
Bei datierten Verweisungen gilt nur die in Bezug genommene Ausgabe.
- bib.al.original-language: en
- bib.dp.publication-date: 2018-07-01
- ids.document: 7104561
- ids.element: section_2
- ids.language-synoptic: section_2
- ids.tracing: hash-821db916888fc1f6800c4d901a4e6394caf878587685c36e0bdc19b86b134bb4
- obj.clause-number: 2
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### tr--570aeb71-321d-47c4-82c1-10e363247405--8jbY0TeC1ECN: Normative Verweisungen (provision)
Bei undatierten Verweisungen gilt die letzte Ausgabe des in Bezug genommenen Dokuments (einschließlich aller Änderungen).
- bib.al.original-language: en
- bib.dp.publication-date: 2018-07-01
- ids.document: 7104561
- ids.element: section_2
- ids.language-synoptic: section_2
- ids.tracing: hash-ab1dc50b621d171b952d9921ff13bfe359008e89379c1039181060d790f19ae8
- obj.clause-number: 2
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-6f89327dc7d8466: Normative Verweisungen (provision)
- DIN 14095, Feuerwehrpläne für bauliche Anlagen^ ^1)
- DIN 14365-1:1991-02, Mehrzweckstrahlrohre PN 16 – Maße, Werkstoffe, Ausführung, Kennzeichnung
- DIN 14365-2:1986-09, Mehrzweckstrahlrohre PN 16 – Anforderungen, Prüfung^1)
- DIN 14366-2:1984-10, Schaumstrahlrohre für Werfer-Unterteile^1)
- DIN EN 2:2005-01, Brandklassen; Deutsche Fassung EN 2:1992 + A1:2004
- DIN EN 3-7:2007-10, Tragbare Feuerlöscher – Teil 7: Eigenschaften, Leistungsanforderungen und Prüfungen; Deutsche Fassung EN 3-7:2004 + A1:2007
- DIN EN 615:2009-08, Brandschutz – Löschmittel – Anforderungen an Löschpulver (nicht für Löschpulver der Brandklasse D); Deutsche Fassung EN 615:2009
- DIN EN 1568 (alle Teile), Feuerlöschmittel – Schaummittel
- DIN EN 15182-1:2010-04, Strahlrohre für die Brandbekämpfung – Teil 1: Allgemeine Anforderungen; Deutsche Fassung EN 15182-1:2007 + A1:2009
- DIN EN 15182-2:2010-04, Strahlrohre für die Brandbekämpfung – Teil 2: Hohlstrahlrohre PN 16; Deutsche Fassung EN 5182-2:2007 + A1:2009
- DIN EN 15182-3:2010-04, Strahlrohre für die Brandbekämpfung – Teil 3: Strahlrohre mit Vollstrahl und/oder einem unveränderlichen Sprühstrahlwinkel PN 16; Deutsche Fassung EN 15182-3:2007 + A1:2009
- DIN EN 15182-4:2010-04, Strahlrohre für die Brandbekämpfung – Teil 4: Hochdruckstrahlrohre PN 40; Deutsche Fassung EN 15182-4:2007 + A1:2009
- DIN EN 15767-3:2010-12, Tragbare Geräte zum Ausbringen von Löschmitteln, welche mit Feuerlöschpumpen gefördert werden – Tragbare Werfer – Teil 3: Schaumdüsen; Deutsche Fassung EN 15767-3:2010
- DIN EN 16327:2014-07, Feuerwehrwesen – Druckzumischanlagen (DZA) und Druckluftschaumanlagen (DLS); Deutsche Fassung EN 16327:2014
- DIN EN 16712-3:2015-12, Tragbare Geräte zum Ausbringen von Löschmitteln, die mit Feuerlöschpumpen gefördert werden – Tragbare Schaumgeräte – Teil 3: Schwer- und Mittelschaumrohre PN 16; Deutsche Fassung EN°16712-3:2015
- DIN EN 50122-1 (VDE 0115-3):2017-10 , Bahnanwendungen – Ortsfeste Anlagen – Elektrische Sicherheit, Erdung und Rückleitung – Teil 1: Schutzmaßnahmen gegen elektrischen Schlag; Deutsche Fassung EN 50122-1:2011 + A1:2011 + AC:2012 + AC:2016 + A3:2016 + A4:2017
- DIN EN 62040-1 (VDE 0558-510):2013-11 , Unterbrechungsfreie Stromversorgungssysteme (USV) – Teil 1: Allgemeine Anforderungen und Sicherheitsanforderungen (IEC 62040-1:2008 + Corrigendum September 2008 + A1:2013); Deutsche Fassung EN 62040-1:2008 + Corrigendum Februar 2009 + A1:2013
- DIN VDE 0105-100 (VDE 0105-100):2015-10 , Betrieb von elektrischen Anlagen – Teil 100: Allgemeine Festlegungen
- DIN VDE 0105-103 (VDE 0105-103):2014-10 , Betrieb von elektrischen Anlagen – Zusatzfestlegungen für Bahnen
- E DIN IEC 62335 (VDE 0661-20):2008-08, Ortsveränderliche Fehlerstrom-Schutzeinrichtungen mit geschaltetem Schutzleiter zur Anwendung für Geräte der Schutzklasse I und für batteriebetriebene Fahrzeuge (IEC 23E/632/CDV:2007)
- DIN EN ISO 7010, Graphische Symbole – Sicherheitsfarben und Sicherheitszeichen – Registrierte Sicherheitszeichen
- IEC 60417-DB:2010, Graphische Symbole für Betriebsmittel
- Feuerwehrdienstvorschrift 500, Einheiten im ABC-Einsatz ^ ^2)
- DGUV Information 204-006, Anleitung zur Ersten Hilfe ^ ^3)
- DGUV Fachinformation, 2016-09, Stromunfall - Ärztliche Vorstellung notwendig ^ ^3)
- bib.al.original-language: en
- bib.dp.publication-date: 2018-07-01
- ids.document: 7104561
- ids.element: section_2
- ids.language-synoptic: section_2
- ids.tracing: hash-d2d34f491f17907af4afb6908cdff846f2fc82e9101669b108ed4da109297cfd
- obj.clause-number: 2
- obj.element-name: list-of-documents
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-7a45e2832a99448: Normative Verweisungen (provision)
^1)
Zurückgezogen.
- bib.al.original-language: en
- bib.dp.publication-date: 2018-07-01
- ids.document: 7104561
- ids.element: section_2
- ids.language-synoptic: section_2
- ids.tracing: hash-d540af5aa0a2ed12dfce9361af3d8f3f65789242a070ba80490ad196ac8e68ae
- obj.clause-number: 2
- obj.element-name: footnote
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

#### prov-7104561-ebc47087836d45a: Normative Verweisungen (provision)
^2)
Zu beziehen bei: Ausschuss Feuerwehrangelegenheiten, Katastrophenschutz und zivile Verteidigung (AFKzV). Diese Dienstvorschrift wurde vom AFKzV den Ländern zur Einführung empfohlen.
- bib.al.original-language: en
- bib.dp.publication-date: 2018-07-01
- ids.document: 7104561
- ids.element: section_2
- ids.language-synoptic: section_2
- ids.tracing: hash-2cdc77357e457d7fc52f6e2baf980d21df2c9f6c741fdf4711acfe0f5139c71d
- obj.clause-number: 2
- obj.element-name: footnote
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

#### prov-7104561-f577ae60f247468: Normative Verweisungen (provision)
^3)
Zu beziehen bei: DGUV Deutsche Gesetzliche Unfallversicherung.
- bib.al.original-language: en
- bib.dp.publication-date: 2018-07-01
- ids.document: 7104561
- ids.element: section_2
- ids.language-synoptic: section_2
- ids.tracing: hash-56845993f4bf871301ea3d241ff1195eff9d3cc3f4b6c0a31654e2f90382b5e7
- obj.clause-number: 2
- obj.element-name: footnote
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

#### prov-7104561-8d9207967cba450: Normative Verweisungen (provision)
^3)
Zu beziehen bei: DGUV Deutsche Gesetzliche Unfallversicherung.
- bib.al.original-language: en
- bib.dp.publication-date: 2018-07-01
- ids.document: 7104561
- ids.element: section_2
- ids.language-synoptic: section_2
- ids.tracing: hash-4067c32160e7838bf64b32cf5247d344408c83c0261f71cdda0816462cd3d199
- obj.clause-number: 2
- obj.element-name: footnote
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

## prov-7104561-019c2d7e0360426: Begriffe (heading)
- bib.al.original-language: en
- bib.dp.publication-date: 2018-07-01
- ids.document: 7104561
- ids.element: section_3
- ids.language-synoptic: section_3
- ids.tracing: hash-bc1c65c2b0a57898b92b0f9f2049e589792f38f0bd872d65cc53454b57a9f01b
- obj.clause-number: 3
- obj.element-name: heading
- obj.language: de
- obj.specobject-type: heading
- ChapterName: 3 Begriffe

### tr--570aeb71-321d-47c4-82c1-10e363247405--AHWRlWqjuTdc: Begriffe (provision)
Für die Anwendung dieses Dokuments gelten die folgenden Begriffe.
- bib.al.original-language: en
- bib.dp.publication-date: 2018-07-01
- ids.document: 7104561
- ids.element: section_3
- ids.language-synoptic: section_3
- ids.tracing: hash-7eab92ed5c878cbb0a9d9436637edd6ea9305bd0d1f5f9f963b1b690f1b53701
- obj.clause-number: 3
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-87471f9fcd0f46d: abgeschlossene elektrische Betriebsstätte (provision)
3.1
abgeschlossene elektrische Betriebsstätte
Raum oder ein Ort, der ausschließlich zum Betrieb elektrischer Anlagen dient und unter Verschluss gehalten wird. Zutritt haben Elektrofachkräfte und elektrotechnisch unterwiesene Personen, Laien jedoch nur in Begleitung von Elektrofachkräften oder elektrotechnisch unterwiesenen Personen.
Anmerkung 1 zum Begriff: Hierzu gehören z. B. abgeschlossene Schalt- und Verteilungsanlagen, Transformatorzellen, Schaltfelder, Maststationen.
[QUELLE: DIN VDE 0105-100 (VDE 0105-100):2015-10 ]
- bib.al.original-language: en
- bib.dp.publication-date: 2018-07-01
- ids.document: 7104561
- ids.element: sub-3.1
- ids.language-synoptic: sub-3.1
- ids.tracing: hash-5a4c1437a869e3d30c878fcc701cb078bc287ef2a96d436425ff3cfcd6845021
- obj.clause-number: 3.1
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-bc246b55dc6645d: Anlagenverantwortlicher (provision)
3.2
Anlagenverantwortlicher
eine Person, die beauftragt ist, während der Durchführung von Arbeiten die unmittelbare Verantwortung für den sicheren Betrieb der elektrischen Anlage zu tragen, die zur Arbeitsstelle gehört
Anmerkung 1 zum Begriff: Der Anlagenverantwortliche hat die möglichen Auswirkungen der Arbeiten auf die elektrische Anlage oder die Teile davon, die in seiner Verantwortung stehen, sowie die Auswirkungen der elektrischen Anlage auf die Arbeitsstelle und die arbeitenden Personen zu beurteilen. Erforderlichenfalls können einige mit dieser Verantwortung einhergehende Verpflichtungen auf andere Personen übertragen werden (siehe auch DIN VDE 0105-100 (VDE 0105-100):2015-10, 4.3 ).
[QUELLE: DIN VDE 0105-100 (VDE 0105-100):2015-10 , modifiziert, Anmerkung 2 wurde nicht übernommen.]
- bib.al.original-language: en
- bib.dp.publication-date: 2018-07-01
- ids.document: 7104561
- ids.element: sub-3.2
- ids.language-synoptic: sub-3.2
- ids.tracing: hash-a33fbcd16b973806afe956921336ba27cf869b6ac2febd698df349f79662d1fb
- obj.clause-number: 3.2
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-034488baff1f47e: Anlagenbetreiber (provision)
3.3
Anlagenbetreiber
Person mit der Gesamtverantwortung für den sicheren Betrieb der elektrischen Anlage, die Regeln und Randbedingungen der Organisation vorgibt
Anmerkung 1 zum Begriff: Diese Person kann der Eigentümer, Unternehmer, Besitzer oder eine beauftragte Person sein, die die Unternehmerpflichten wahrnimmt.
Anmerkung 2 zum Begriff: Erforderlichenfalls können einige mit dieser Verantwortung einhergehende Verpflichtungen auf andere Personen übertragen werden. Bei umfangreichen oder komplexen Anlagen kann diese Zuständigkeit auch für Teilanlagen übertragen sein (siehe auch DIN VDE 0105-100 (VDE 0105-100):2015-10, 4.3 ).
[QUELLE: DIN VDE 0105-100 (VDE 0105-100):2015-10 , modifiziert, Anmerkung 3 wurde nicht übernommen.]
- bib.al.original-language: en
- bib.dp.publication-date: 2018-07-01
- ids.document: 7104561
- ids.element: sub-3.3
- ids.language-synoptic: sub-3.3
- ids.tracing: hash-3ba90a4746350f6db544ba5d43bd2c35659a2e61ec59958aa1dee73590fbb132
- obj.clause-number: 3.3
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-e729dc7ac05248f: automatische Brandmeldeanlagen (provision)
3.4
automatische Brandmeldeanlagen
Einrichtungen, die den Zweck haben, Schadenfeuer zum frühestmöglichen Zeitpunkt zu erkennen und so zu melden, dass geeignete Gegenmaßnahmen ergriffen werden können (z. B. Räumung von Gebäuden, Herbeirufen von Löschkräften, selbsttätiges Auslösen von Löschvorgängen, Schließen von Feuerschutzabschlüssen, Steuern von Klima- und Lüftungsanlagen)
- bib.al.original-language: en
- bib.dp.publication-date: 2018-07-01
- ids.document: 7104561
- ids.element: sub-3.4
- ids.language-synoptic: sub-3.4
- ids.tracing: hash-8b0f321be50d0b09cd0d45b34e4f4ff8e1cc4695d9cabe878492b24a66fb0f61
- obj.clause-number: 3.4
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-302af75ef06e4fd: Brandklassen (provision)
3.5
Brandklassen
Einteilung von Bränden in Abhängigkeit des Brennstoffes
Anmerkung 1 zum Begriff: Nach DIN EN 2 werden folgende Brandklassen unterschieden.
- bib.al.original-language: en
- bib.dp.publication-date: 2018-07-01
- ids.document: 7104561
- ids.element: sub-3.5
- ids.language-synoptic: sub-3.5
- ids.tracing: hash-f47308a14eb4cf98f1a120f287176757f040c170ccbb0126586455166fbb7530
- obj.clause-number: 3.5
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-6ab2c73a57e0478: Brandklasse A (provision)
3.5.1
Brandklasse A
Brände fester Stoffe, hauptsächlich organischer Natur, die normalerweise unter Glutbildung verbrennen, z. B. Holz, Papier, Stroh, Textilien, Kohle
- bib.al.original-language: en
- bib.dp.publication-date: 2018-07-01
- ids.document: 7104561
- ids.element: sub-3.5.1
- ids.language-synoptic: sub-3.5.1
- ids.tracing: hash-2972f7fd4c024a40373b4d847bf4d857c98cd5d742ce6af9fda38750ee5003c6
- obj.clause-number: 3.5.1
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-0e361f89e705463: Brandklasse B (provision)
3.5.2
Brandklasse B
Brände von flüssigen oder flüssig werdenden Stoffen, z. B. Benzin, Benzol, Öle, Fette, Lacke, Teer, Äther, Alkohol, Stearin, Paraffin
- bib.al.original-language: en
- bib.dp.publication-date: 2018-07-01
- ids.document: 7104561
- ids.element: sub-3.5.2
- ids.language-synoptic: sub-3.5.2
- ids.tracing: hash-7da7063532192cd8b1f95d5c22febb07ec76ff90dbda7da857eca9093010e718
- obj.clause-number: 3.5.2
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-0118f872aae946f: Brandklasse C (provision)
3.5.3
Brandklasse C
Brände von Gasen, z. B. Methan, Propan, Wasserstoff, Acetylen, Erdgas
- bib.al.original-language: en
- bib.dp.publication-date: 2018-07-01
- ids.document: 7104561
- ids.element: sub-3.5.3
- ids.language-synoptic: sub-3.5.3
- ids.tracing: hash-d78a1204583e79ef1e5014a1bab44c398d72dab495537faec09281d9171708e3
- obj.clause-number: 3.5.3
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-471e1c0032a1429: Brandklasse D (provision)
3.5.4
Brandklasse D
Brände von Metallen, z. B. Aluminium, Magnesium und ihre Legierungen, Natrium, Kalium
- bib.al.original-language: en
- bib.dp.publication-date: 2018-07-01
- ids.document: 7104561
- ids.element: sub-3.5.4
- ids.language-synoptic: sub-3.5.4
- ids.tracing: hash-2560783041d4911495fd11257d574d6c4cdddcf11853a04f897eb46ab30fa6ad
- obj.clause-number: 3.5.4
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-6df6c26bace74a5: Brandklasse F (provision)
3.5.5
Brandklasse F
Brände von Speiseölen/-fetten (pflanzliche oder tierische Öle und Fette) in Frittier- und Fettbackgeräten und anderen Kücheneinrichtungen und -geräten
- bib.al.original-language: en
- bib.dp.publication-date: 2018-07-01
- ids.document: 7104561
- ids.element: sub-3.5.5
- ids.language-synoptic: sub-3.5.5
- ids.tracing: hash-2650e3853b3c559df384387fd101ce987b6f51282ddcafb78f9965abababd169
- obj.clause-number: 3.5.5
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-ab01431085ef4e6: dezentrale Stromerzeugungsanlagen (provision)
3.6
dezentrale Stromerzeugungsanlagen
Anlagen zur Erzeugung von elektrischem Strom für den Eigenverbrauch und/oder zur Einspeisung in das öffentliche Energieversorgungsnetz
Anmerkung 1 zum Begriff: Dazu gehören z. B. Photovoltaik-Stromversorgungssysteme (PV-Anlagen), Brennstoffzellenanlagen, Windenergieanlagen. Dezentrale Stromerzeugungsanlagen können mit oder ohne elektrische Energiespeicher betrieben werden.
- bib.al.original-language: en
- bib.dp.publication-date: 2018-07-01
- ids.document: 7104561
- ids.element: sub-3.6
- ids.language-synoptic: sub-3.6
- ids.tracing: hash-cf2ceee6cc1f924c0f5516853fc7cbe36f518354c2bccfc3e798b44756ad7665
- obj.clause-number: 3.6
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-5d0156f91670491: Druckluftschaum (en: compressed air foam) (provision)
3.7
Druckluftschaum (en: compressed air foam)
Löschschaum, erzeugt durch eine Druckluftschaumanlage
Anmerkung 1 zum Begriff: Druckluftschaumanlagen sind in DIN EN 16327 definiert.
- bib.al.original-language: en
- bib.dp.publication-date: 2018-07-01
- ids.document: 7104561
- ids.element: sub-3.7
- ids.language-synoptic: sub-3.7
- ids.tracing: hash-d10c098e1a5b711c0d3e419022aa7bb59d255b12bb4eacab3a93c862b0705432
- obj.clause-number: 3.7
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-53aa6c8e914f421 (provision)
3.8
elektrische Anlage
Anlagen mit elektrischen Betriebsmitteln zur Erzeugung, Übertragung, Umwandlung, Verteilung und Anwendung elektrischer Energie
Den elektrischen Betriebsmitteln gleichgesetzt werden Werkzeuge, Ausrüstungen, Schutz- und Hilfsmittel, soweit an diese Anforderungen hinsichtlich der elektrischen Sicherheit gestellt werden.
Anmerkung 1 zum Begriff: Dies schließt Energiequellen ein wie Batterien, Kondensatoren und alle anderen Quellen gespeicherter elektrischer Energie.
[QUELLE: DIN VDE 0105-100 (VDE 0105-100):2015-10 ]
- bib.al.original-language: en
- bib.dp.publication-date: 2018-07-01
- ids.document: 7104561
- ids.element: section_3.8
- ids.language-synoptic: section_3.8
- ids.tracing: hash-09cc6b33c55cd6f5fb19504ffef7d1d63f4b0c4abfd30d5210c8f05373982a44
- obj.clause-number: 3.8
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-eb22e42d014b474: Elektrofachkraft (provision)
3.9
Elektrofachkraft
ist, wer aufgrund seiner fachlichen Ausbildung, Kenntnisse und Erfahrungen sowie Kenntnis der einschlägigen Normen die ihm übertragenen Arbeiten beurteilen und mögliche Gefahren erkennen kann
Anmerkung 1 zum Begriff: Zur Beurteilung der fachlichen Ausbildung kann auch eine mehrjährige Tätigkeit auf dem betreffenden Arbeitsgebiet herangezogen werden.
[QUELLE: DIN VDE 0105-100 (VDE 0105-100):2015-10 ]
- bib.al.original-language: en
- bib.dp.publication-date: 2018-07-01
- ids.document: 7104561
- ids.element: sub-3.9
- ids.language-synoptic: sub-3.9
- ids.tracing: hash-51a4ce7c10b71707fbbf788688b09c7f23686458d7024f554e80a0bbd8f8a97d
- obj.clause-number: 3.9
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-d5437d5f04fc42c: elektrotechnisch unterwiesene Person (provision)
3.10
elektrotechnisch unterwiesene Person
ist, wer durch eine Elektrofachkraft über die ihr übertragenen Aufgaben und die möglichen Gefahren bei unsachgemäßem Verhalten unterrichtet und erforderlichenfalls angelernt sowie über die notwendigen Schutzeinrichtungen und Schutzmaßnahmen unterwiesen wurde
[QUELLE: DIN VDE 0105-100 (VDE 0105-100):2015-10 ]
- bib.al.original-language: en
- bib.dp.publication-date: 2018-07-01
- ids.document: 7104561
- ids.element: sub-3.10
- ids.language-synoptic: sub-3.10
- ids.tracing: hash-40542dbf6c7f886d24d9a45abc95203a0b4f2dd659177b37e110791214bf346f
- obj.clause-number: 3.10
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-d67463fba4e14d0: fahrbare Feuerlöscher (provision)
3.11
fahrbare Feuerlöscher
fahrbare Feuerlöschgeräte ohne eigenen Kraftantrieb
- bib.al.original-language: en
- bib.dp.publication-date: 2018-07-01
- ids.document: 7104561
- ids.element: sub-3.11
- ids.language-synoptic: sub-3.11
- ids.tracing: hash-4da202e4083f7a38d9ce0bb0bad259d8387a64a64dac790b458828eb9f36d8ed
- obj.clause-number: 3.11
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-96953cc8e3df4e9 (provision)
3.12
Fahrleitung
Leitersystem zur Versorgung von Fahrzeugen mit elektrischer Energie über Stromabnahmeeinrichtungen
Anmerkung 1 zum Begriff: Es umfasst alle Leiter, die zur Stromabnahme nötig sind, sowie Stromschienen und beinhaltet Folgendes:
- Verstärkungsleitungen,
- Schalterquerleitungen,
- Trennschalter,
- Streckentrenner,
- Überspannungsschutzeinrichtungen,
- Trageinrichtungen, die nicht von den Leitern isoliert sind,
- Isolatoren, die mit aktiven Teilen verbunden sind.
Nicht zur Fahrleitung gehören:
- Speiseleitungen,
- Erdseile und Rückleiter.
[QUELLE: DIN EN 50122-1 (VDE 0115-3):2017-10 ]
- bib.al.original-language: en
- bib.dp.publication-date: 2018-07-01
- ids.document: 7104561
- ids.element: section_3.12
- ids.language-synoptic: section_3.12
- ids.tracing: hash-6aeda75546d20b05c99d981343d51117fb41393410ef2ff52169127f61f915e5
- obj.clause-number: 3.12
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-fd991a4cc73746f: Freileitung (provision)
3.13
Freileitung
elektrische Leitung, deren Leiter oberirdisch geführt sind, im Allgemeinen mit Hilfe von Isolatoren und geeigneten Stützpunkten
Anmerkung 1 zum Begriff: Bestimmte Freileitungen können mit isolierten Leitern ausgerüstet sein.
[QUELLE: IEV 466-01-02]
- bib.al.original-language: en
- bib.dp.publication-date: 2018-07-01
- ids.document: 7104561
- ids.element: sub-3.13
- ids.language-synoptic: sub-3.13
- ids.tracing: hash-f714783f11653ff27e80735c17bffeb77a94942b51e98bc459630868c709c161
- obj.clause-number: 3.13
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-2da2c2f556d9461: Hochvolt HV (provision)
3.14
Hochvolt HV
Spannungen oberhalb von AC 25 V oder DC 60 V in Elektrofahrzeugen
Anmerkung 1 zum Begriff: Dies schließt Fahrzeuge mit Hybridantrieben und Fahrzeuge mit Brennstoffzellenantrieben ein.
- bib.al.original-language: en
- bib.dp.publication-date: 2018-07-01
- ids.document: 7104561
- ids.element: sub-3.14
- ids.language-synoptic: sub-3.14
- ids.tracing: hash-c8b6fe1c5211e168a388eb68cb48ab3f33a07c2f1402ced1c5df406181d2cc3a
- obj.clause-number: 3.14
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-ed71785c485e45a: Hochspannungsanlage (provision)
3.15
Hochspannungsanlage
elektrische Anlage, die mit einer Nennspannung größer AC 1 000 V (Wechselspannung) oder DC 1 500 V (Gleichspannung) betrieben wird
Anmerkung 1 zum Begriff: Zu den Hochspannungsanlagen gehören insbesondere Anlagen, die der Stromerzeugung oder der Umwandlung, Verteilung und Anwendung elektrischer Energie dienen, z. B. Kraftwerke, Schalt- und Umspannanlagen, Freileitungen, Kabelanlagen sowie Anlagen und Fahrzeuge von elektrischen Bahnen.
Anmerkung 2 zum Begriff: Hochspannungsanlagen – mit Ausnahme von Freileitungen und Fahrleitungen elektrischer Bahnen – sind in der Regel durch das Warnschild W012 „Warnung vor elektrischer Spannung“ nach DIN EN ISO 7010 oder Warnschild „gefährliche Spannung“ nach IEC 60417-5036 gekennzeichnet.
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Anmerkung 3 zum Begriff:
- bib.al.original-language: en
- bib.dp.publication-date: 2018-07-01
- ids.document: 7104561
- ids.element: sub-3.15
- ids.language-synoptic: sub-3.15
- ids.tracing: hash-39dc352453d4748a97ca6f940c382d00565642905c60e1cb54ac7ad02392a27b
- obj.clause-number: 3.15
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-1d7cdf44533a4e6: Niederspannungsanlage (provision)
3.16
Niederspannungsanlage
elektrische Anlage, die mit einer Nennspannung kleiner oder gleich AC 1 000 V (Wechselspannung) oder DC 1 500 V (Gleichspannung) betrieben wird
Anmerkung 1 zum Begriff: Zu den Niederspannungsanlagen gehören z. B. Stromerzeugungs- und Verteilungsanlagen, Ortsnetze, Hausinstallationen sowie Installationen für industrielle, gewerbliche und landwirtschaftliche Betriebe, die Fahrleitungen und Installationen der mit Gleichspannung (Niederspannung) betriebenen Straßen- und Stadtbahnen, Oberleitungsbusse (Obusse), Fernmelde- und Informationsverarbeitungsanlagen.
- bib.al.original-language: en
- bib.dp.publication-date: 2018-07-01
- ids.document: 7104561
- ids.element: sub-3.16
- ids.language-synoptic: sub-3.16
- ids.tracing: hash-d84114f7bcf5a38008e75e2a33f38fa1e833b1e14c848621b9fd7be00cd13b97
- obj.clause-number: 3.16
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-7f5b9e9fd6974a1: ortsfeste Löschanlagen (provision)
3.17
ortsfeste Löschanlagen
fest installierte Löscheinrichtungen, deren Auslösung von Hand und/oder automatisch erfolgt
- bib.al.original-language: en
- bib.dp.publication-date: 2018-07-01
- ids.document: 7104561
- ids.element: sub-3.17
- ids.language-synoptic: sub-3.17
- ids.tracing: hash-f877f37e7c7a898725aec815ae9fde024b4a2a035410916843aa88b9f5e912cf
- obj.clause-number: 3.17
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-bb7ab81a359548a: SPE-PRCD (provision)
3.18
SPE-PRCD
Differenzstromeinrichtung mit Fehlerstrom-, Schutzleiterbruch-, Schutzleiterspannungs- und Fremdspannungsüberwachung
[QUELLE: E DIN IEC 62335 (VDE 0661-20):2008-06]
- bib.al.original-language: en
- bib.dp.publication-date: 2018-07-01
- ids.document: 7104561
- ids.element: sub-3.18
- ids.language-synoptic: sub-3.18
- ids.tracing: hash-04912881b6e4eedbaf4be1ab6058829952d7abef77eebd6f208bb41178a4f001
- obj.clause-number: 3.18
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-d00c38bee6564c0: Strahlrohr (provision)
3.19
Strahlrohr
Armaturen zur Abgabe von Löschmitteln
- bib.al.original-language: en
- bib.dp.publication-date: 2018-07-01
- ids.document: 7104561
- ids.element: sub-3.19
- ids.language-synoptic: sub-3.19
- ids.tracing: hash-d818843ffe2fd225994c78206f8aa6c34c398aa609a271e21526efe258bbc745
- obj.clause-number: 3.19
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-523ae53802cd466: anderes Strahlrohr (provision)
3.19.1
anderes Strahlrohr
Strahlrohr, das weder Mehrzweckstrahlrohr noch Hohlstrahlrohr ist
- bib.al.original-language: en
- bib.dp.publication-date: 2018-07-01
- ids.document: 7104561
- ids.element: sub-3.19.1
- ids.language-synoptic: sub-3.19.1
- ids.tracing: hash-8bb43fbf495b8daf8aa6479efc541a2ed57eacdeab87a6e97d69411882fd0be8
- obj.clause-number: 3.19.1
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-ce452401e808483: Hohlstrahlrohr (provision)
3.19.2
Hohlstrahlrohr
Strahlrohr einschließlich einer Schließvorrichtung und einer einstellbaren Strahlform
[QUELLE: DIN EN 15182-2:2010-04, 3.1, verändert übernommen]
- bib.al.original-language: en
- bib.dp.publication-date: 2018-07-01
- ids.document: 7104561
- ids.element: sub-3.19.2
- ids.language-synoptic: sub-3.19.2
- ids.tracing: hash-cc483f6fbaf80c4105540a3dac469e71c9e3eb651abddab0d5086866563c5015
- obj.clause-number: 3.19.2
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-784459f1d4564d7: Mehrzweckstrahlrohr (provision)
3.19.3
Mehrzweckstrahlrohr
Das Mehrzweckstrahlrohr ist eine Armatur zur gezielten Abgabe vornehmlich von Löschwasser in Form eines Voll- oder Sprühstrahls
Anmerkung 1 zum Begriff: Strahlrohre CM haben einen Mundstückdurchmesser von 9 mm und einen Düsendurchmesser von 12 mm.
Anmerkung 2 zum Begriff: Strahlrohre BM haben einen Mundstückdurchmesser von 16 mm und einen Düsendurchmesser von 22 mm.
[QUELLE: DIN 14365-1:1991-02]
- bib.al.original-language: en
- bib.dp.publication-date: 2018-07-01
- ids.document: 7104561
- ids.element: sub-3.19.3
- ids.language-synoptic: sub-3.19.3
- ids.tracing: hash-e470d668507655895bbcd7f31328ab19c22c5183d1b9990c14b08ef82c698eb8
- obj.clause-number: 3.19.3
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-051d7a050a5a49a: tragbarer Feuerlöscher (provision)
3.20
tragbarer Feuerlöscher
Feuerlöscher, der getragen und von Hand bedient werden kann und im betriebsbereiten Zustand eine Masse von nicht mehr als 20 kg hat
[QUELLE: DIN EN 3-7:2007-10]
- bib.al.original-language: en
- bib.dp.publication-date: 2018-07-01
- ids.document: 7104561
- ids.element: sub-3.20
- ids.language-synoptic: sub-3.20
- ids.tracing: hash-f189926c259d1e8ce24831c9d58ae8132db9f72eaf1ac3d3737132d2d55a812c
- obj.clause-number: 3.20
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-ecc64cb60d8e4d1 (provision)
3.21
trockener Raum
Raum oder bestimmter Bereich innerhalb eines Raums, in dem in der Regel kein Kondenswasser auftritt oder in dem die Luft nicht mit Feuchtigkeit gesättigt ist
Anmerkung 1 zum Begriff: Hierzu gehören z. B. Wohnräume (auch Hotelzimmer), Büros; weiterhin können hierzu gehören:
- Geschäftsräume, Verkaufsräume, Dachböden, Treppenhäuser, beheizte oder belüftbare Keller;
- Küchen in Wohnungen und Baderäume in Wohnungen und Hotels gelten in Bezug auf die Installation als trockene Räume, da in ihnen nur zeitweise Feuchtigkeit auftritt.
- bib.al.original-language: en
- bib.dp.publication-date: 2018-07-01
- ids.document: 7104561
- ids.element: section_3.21
- ids.language-synoptic: section_3.21
- ids.tracing: hash-6e000676e3686a713e477cd84b430797476b3b610b95262d7855ae0f52511d51
- obj.clause-number: 3.21
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-016a9b7a09e4466: unterbrechungsfreies Stromversorgungssystem USV (provision)
3.22
unterbrechungsfreies Stromversorgungssystem USV
Kombination von Stromrichtern, Schaltern und Energiespeichern (wie Batterien), die ein Stromversorgungssystem bildet, das bei Ausfall der Eingangsversorgung eine beständige Versorgung der Last sicherstellt
[QUELLE: DIN EN 62040-1 (VDE 0558-510):2009-06 ]
- bib.al.original-language: en
- bib.dp.publication-date: 2018-07-01
- ids.document: 7104561
- ids.element: sub-3.22
- ids.language-synoptic: sub-3.22
- ids.tracing: hash-308a436f3dadf8d2d386340581c130f2ff53c06e4729a6b7504411539cbf89c0
- obj.clause-number: 3.22
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

## prov-7104561-5c875132a1f5470: Vorbereitende Maßnahmen (heading)
- bib.al.original-language: en
- bib.dp.publication-date: 2018-07-01
- ids.document: 7104561
- ids.element: section_4
- ids.language-synoptic: section_4
- ids.tracing: hash-70bedd9ad1d386d010630d2c96595bfc84b81b13c069abdd1e65bbecee49176f
- obj.clause-number: 4
- obj.element-name: heading
- obj.language: de
- obj.specobject-type: heading
- ChapterName: 4 Vorbereitende Maßnahmen

### prov-7104561-4827e155230c469: 4.1 (heading)
- bib.al.original-language: en
- bib.dp.publication-date: 2018-07-01
- ids.document: 7104561
- ids.element: section_4.1
- ids.language-synoptic: section_4.1
- ids.tracing: hash-b846c4c6c592deb2a0fe3f0affc7e9b93d286954082ff317f215a84f4eb47751
- obj.element-name: heading
- obj.language: de
- obj.specobject-type: heading

#### tr--570aeb71-321d-47c4-82c1-10e363247405--KSHWBbUkLG91 (provision)
Verständnisvolle Zusammenarbeit zwischen Feuerwehr und dem Anlagenbetreiber elektrischer Anlagen ist anzustreben.
- bib.al.original-language: en
- bib.dp.publication-date: 2018-07-01
- ids.document: 7104561
- ids.element: section_4.1
- ids.language-synoptic: section_4.1
- ids.tracing: hash-074c3735b63be0fdb109a2f795b9f49d020b1f8c7055d1269b970a41c2f9d81e
- obj.clause-number: 4.1
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

#### tr--570aeb71-321d-47c4-82c1-10e363247405--eUHtNI5YFoBD (provision)
Diesem Zweck dienen unter anderem die Absprachen zwischen Feuerwehr und Anlagenbetreiber über die im Einsatz notwendigen Maßnahmen nach 4.2 bis 4.5.
- bib.al.original-language: en
- bib.dp.publication-date: 2018-07-01
- ids.document: 7104561
- ids.element: section_4.1
- ids.language-synoptic: section_4.1
- ids.tracing: hash-ee9984b3fd293faca96da24cafe9482cdc15f84fdd63a5751b4e27bcdd600fb1
- obj.clause-number: 4.1
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-7104561-645b8e761e7a4d0

### prov-7104561-645b8e761e7a4d0: 4.2 (heading)
- bib.al.original-language: en
- bib.dp.publication-date: 2018-07-01
- ids.document: 7104561
- ids.element: section_4.2
- ids.language-synoptic: section_4.2
- ids.tracing: hash-4b197ad9b12286e63e3a48f8fc3c2cbd29eacba9c60a2aa90b4ea8c543c031f7
- obj.element-name: heading
- obj.language: de
- obj.specobject-type: heading

#### tr--570aeb71-321d-47c4-82c1-10e363247405--YPbxDxmcjluN (provision)
Der Anlagenbetreiber gibt der Feuerwehr Aufklärung über besondere Gefährdungen und Schwierigkeiten, die bei Brandbekämpfung und bei technischer Hilfeleistung auftreten können.
- bib.al.original-language: en
- bib.dp.publication-date: 2018-07-01
- ids.document: 7104561
- ids.element: section_4.2
- ids.language-synoptic: section_4.2
- ids.tracing: hash-00543c24b736b5d0fd91f779fe6d70fd0c238399062085becd81ae7aeb7f73c0
- obj.clause-number: 4.2
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### tr--570aeb71-321d-47c4-82c1-10e363247405--gpPpcUUFRFk9 (provision)
Grundlage können Feuerwehrpläne nach DIN 14095 sein, die der raschen Orientierung und der Beurteilung der Lage dienen.
- bib.al.original-language: en
- bib.dp.publication-date: 2018-07-01
- ids.document: 7104561
- ids.element: section_4.2
- ids.language-synoptic: section_4.2
- ids.tracing: hash-4ffb48e15f5aa3baedd89ca37014a52b85dcbba43628ac2e63039bf746b3a6e8
- obj.clause-number: 4.2
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-dbbfaa73d01043a: 4.3 (heading)
- bib.al.original-language: en
- bib.dp.publication-date: 2018-07-01
- ids.document: 7104561
- ids.element: section_4.3
- ids.language-synoptic: section_4.3
- ids.tracing: hash-a587d260a99f4a176fa85741c8d3d507a35e755a0ac97d8cb1dd642e9da7ba16
- obj.element-name: heading
- obj.language: de
- obj.specobject-type: heading

#### tr--570aeb71-321d-47c4-82c1-10e363247405--wWvxJ8b5mlzk (provision)
Isolier-/Kühl-Flüssigkeiten und -Gase können besondere Gefährdungen darstellen.
- bib.al.original-language: en
- bib.dp.publication-date: 2018-07-01
- ids.document: 7104561
- ids.element: section_4.3
- ids.language-synoptic: section_4.3
- ids.tracing: hash-b8ed7c7abc7a89e3d7e83ed3c4acbc53dcafe1fd9ed42384bdcfe309937158ab
- obj.clause-number: 4.3
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### tr--570aeb71-321d-47c4-82c1-10e363247405--SdyjvC74cmsT (provision)
Einschlägige bundes- und landesrechtliche Festlegungen sind zu beachten.
- bib.al.original-language: en
- bib.dp.publication-date: 2018-07-01
- ids.document: 7104561
- ids.element: section_4.3
- ids.language-synoptic: section_4.3
- ids.tracing: hash-554122efbac2bc02331f72f2bce505cf22679e6cfb89cebca01e1b1eab731732
- obj.clause-number: 4.3
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-28276395737b4ac: , Note (provision)
ANMERKUNG 1:
PCB-haltige elektrische Betriebsmittel sind vom Anlagenbetreiber durch Schilder augenfällig gekennzeichnet.
ANMERKUNG 2 Siehe Anhang A „Beurteilung von Gefahren, die von PCB-haltigen Betriebsmitteln ausgehen können.
- bib.al.original-language: en
- bib.dp.publication-date: 2018-07-01
- ids.document: 7104561
- ids.element: section_4.3
- ids.language-synoptic: section_4.3
- ids.tracing: hash-e4484b7d8c83ec6c6a2db75afeb0155f78b3ba786f4bb6cc360dd0ec0d52c690
- obj.clause-number: 4.3
- obj.element-name: note
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
- cross-reference -> prov-7104561-af1cd1edcd2042c

### prov-7104561-d1bf3c33b594412: 4.4 (heading)
- bib.al.original-language: en
- bib.dp.publication-date: 2018-07-01
- ids.document: 7104561
- ids.element: section_4.4
- ids.language-synoptic: section_4.4
- ids.tracing: hash-47d7042c0ef2a2dc624fb59d93e32fff8b2a205b4a19c120735605c63377802d
- obj.element-name: heading
- obj.language: de
- obj.specobject-type: heading

#### tr--570aeb71-321d-47c4-82c1-10e363247405--hemwSzpElagH (provision)
Den Einsatz einer Werkfeuerwehr und die Einsatzleitung bestimmen landesrechtliche Vorschriften.
- bib.al.original-language: en
- bib.dp.publication-date: 2018-07-01
- ids.document: 7104561
- ids.element: section_4.4
- ids.language-synoptic: section_4.4
- ids.tracing: hash-7e425267c51b906124e809fa86b494e05b132327373ce81ed2e590e911019480
- obj.clause-number: 4.4
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-e00a86eac31c4b4: 4.5 (heading)
- bib.al.original-language: en
- bib.dp.publication-date: 2018-07-01
- ids.document: 7104561
- ids.element: section_4.5
- ids.language-synoptic: section_4.5
- ids.tracing: hash-5118b56b1c582843a87d4e4ed4a28e419fa0cb36f3ca7017e2ec91385e8e3699
- obj.element-name: heading
- obj.language: de
- obj.specobject-type: heading

#### tr--570aeb71-321d-47c4-82c1-10e363247405--DjR7L4mlzjVq (provision)
Der Anlagenbetreiber von Hochspannungsanlagen bezeichnet die Stelle oder nennt Personen, die bei Bränden und technischer Hilfeleistung für den Kontakt mit der Feuerwehr zuständig sind, und gibt die in Frage kommenden Kommunikationsmöglichkeiten bekannt.
- bib.al.original-language: en
- bib.dp.publication-date: 2018-07-01
- ids.document: 7104561
- ids.element: section_4.5
- ids.language-synoptic: section_4.5
- ids.tracing: hash-823f0535586b3dacd55a3badd66e0bcfa2e6a3c3a3dc00d8ad418530a0ff3dd2
- obj.clause-number: 4.5
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

## prov-7104561-7ca7e0b5e4d548a: Maßnahmen bei Bränden und technischen Hilfeleistungen (heading)
- bib.al.original-language: en
- bib.dp.publication-date: 2018-07-01
- ids.document: 7104561
- ids.element: section_5
- ids.language-synoptic: section_5
- ids.tracing: hash-76669df863990e45934b7fb9cf37e246b2a463feb9098cf18ad512cbae81cadb
- obj.clause-number: 5
- obj.element-name: heading
- obj.language: de
- obj.specobject-type: heading
- ChapterName: 5 Maßnahmen bei Bränden und technischen Hilfeleistungen

### prov-7104561-0d3187e259d14fc: Allgemeine Maßnahmen (heading)
- bib.al.original-language: en
- bib.dp.publication-date: 2018-07-01
- ids.document: 7104561
- ids.element: section_5.1
- ids.language-synoptic: section_5.1
- ids.tracing: hash-961582cc37ba8e6b5b0f0a4a695081ce3ab11486ebc4e2695a02bb49bc46cf43
- obj.clause-number: 5.1
- obj.element-name: heading
- obj.language: de
- obj.specobject-type: heading
- ChapterName: 5.1 Allgemeine Maßnahmen

#### prov-7104561-54851de7c0dd446: 5.1.1 (heading)
- bib.al.original-language: en
- bib.dp.publication-date: 2018-07-01
- ids.document: 7104561
- ids.element: section_5.1.1
- ids.language-synoptic: section_5.1.1
- ids.tracing: hash-877d2e5a6eb972b3fcc1c19ab3e87c65fb3f3505d29cf804c50de522474cf2f5
- obj.element-name: heading
- obj.language: de
- obj.specobject-type: heading

##### tr--570aeb71-321d-47c4-82c1-10e363247405--5mYWcerc3YeR (provision)
Feuerwehr und Anlagenbetreiber verständigen sich im Brandfall und bei technischer Hilfeleistung entsprechend den getroffenen Vereinbarungen gegenseitig.
- bib.al.original-language: en
- bib.dp.publication-date: 2018-07-01
- ids.document: 7104561
- ids.element: section_5.1.1
- ids.language-synoptic: section_5.1.1
- ids.tracing: hash-2132d3b5a409a0ec0ee192bc317e9ce81dc68a2ef75af09a23944acc2e143ba1
- obj.clause-number: 5.1.1
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-130fa398fcc44fc: 5.1.2 (heading)
- bib.al.original-language: en
- bib.dp.publication-date: 2018-07-01
- ids.document: 7104561
- ids.element: section_5.1.2
- ids.language-synoptic: section_5.1.2
- ids.tracing: hash-c30abc946bc9bc1b5bb028eac55637c99426a570b314d5c2aae91773dffb2995
- obj.element-name: heading
- obj.language: de
- obj.specobject-type: heading

##### tr--570aeb71-321d-47c4-82c1-10e363247405--L6IDpHLqFZkp (provision)
Beauftragte des Anlagenbetreibers haben sich auf Anforderung der Feuerwehr zur Verfügung zu stellen und erforderlichenfalls auszuweisen.
- bib.al.original-language: en
- bib.dp.publication-date: 2018-07-01
- ids.document: 7104561
- ids.element: section_5.1.2
- ids.language-synoptic: section_5.1.2
- ids.tracing: hash-788fd6f3413502bc4160031c8af38c778eb36904acfc7954c71d74ada3397de0
- obj.clause-number: 5.1.2
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-61233a5507d04b5: 5.1.3 (heading)
- bib.al.original-language: en
- bib.dp.publication-date: 2018-07-01
- ids.document: 7104561
- ids.element: section_5.1.3
- ids.language-synoptic: section_5.1.3
- ids.tracing: hash-9f144f5ae49ae69a374ca57c87a617db80192e809f44466334ecb7d99878ef36
- obj.element-name: heading
- obj.language: de
- obj.specobject-type: heading

##### tr--570aeb71-321d-47c4-82c1-10e363247405--wKkjxRC9440I (provision)
Maßnahmen bei Überflutung zur Sicherstellung der Personensicherheit.
- bib.al.original-language: en
- bib.dp.publication-date: 2018-07-01
- ids.document: 7104561
- ids.element: section_5.1.3
- ids.language-synoptic: section_5.1.3
- ids.tracing: hash-fa0b44dd6f42267dee08f5ea16ff00fe39ae8f1800f41c6b24152d221220b402
- obj.clause-number: 5.1.3
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### tr--570aeb71-321d-47c4-82c1-10e363247405--muQJtDPMkwrf (provision)
Durch Überflutungen (z. B. Rohrbrüche, Hochwasser, Löschwasser) können unter Spannung stehende Teile mit Wasser in Berührung kommen und Personen gefährden.
- bib.al.original-language: en
- bib.dp.publication-date: 2018-07-01
- ids.document: 7104561
- ids.element: section_5.1.3
- ids.language-synoptic: section_5.1.3
- ids.tracing: hash-3799f884948e954e385ad3ee8650e5958bbfb7a9426bad61a66e9ac6131b6c6e
- obj.clause-number: 5.1.3
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### tr--570aeb71-321d-47c4-82c1-10e363247405--BUEdxFHAsf3B (provision)
Diese Bereiche sind rechtzeitig an sicherer Stelle frei- oder auszuschalten.
- bib.al.original-language: en
- bib.dp.publication-date: 2018-07-01
- ids.document: 7104561
- ids.element: section_5.1.3
- ids.language-synoptic: section_5.1.3
- ids.tracing: hash-c01acb52633348e6e4be0d10266c8ca381d1f41c7473ae7c4bcadafb1a4f0409
- obj.clause-number: 5.1.3
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### tr--570aeb71-321d-47c4-82c1-10e363247405--1ezF1r6K2lDh (provision)
Sind elektrische Anlagen bereits überflutet, dürfen diese Bereiche nur nach festgestellter Spannungsfreiheit betreten werden.
- bib.al.original-language: en
- bib.dp.publication-date: 2018-07-01
- ids.document: 7104561
- ids.element: section_5.1.3
- ids.language-synoptic: section_5.1.3
- ids.tracing: hash-e02aa269e142b7649708cdd77db74bac265c37600d1e9b518469d3f5e497543a
- obj.clause-number: 5.1.3
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### tr--570aeb71-321d-47c4-82c1-10e363247405--HXUUTEsKNyNX (provision)
Der zuständige Netzbetreiber ist zu informieren.
- bib.al.original-language: en
- bib.dp.publication-date: 2018-07-01
- ids.document: 7104561
- ids.element: section_5.1.3
- ids.language-synoptic: section_5.1.3
- ids.tracing: hash-31152bc2afc983ad2ed744b917a978ff708397c3e4ac1e9842463f09bc6336bf
- obj.clause-number: 5.1.3
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### tr--570aeb71-321d-47c4-82c1-10e363247405--awU904U48IiN (provision)
Dieser lässt die erforderlichen Freischaltmaßnahmen durchführen oder entscheidet, dass die überfluteten unter Spannung stehenden Anlagen weiter betrieben werden.
- bib.al.original-language: en
- bib.dp.publication-date: 2018-07-01
- ids.document: 7104561
- ids.element: section_5.1.3
- ids.language-synoptic: section_5.1.3
- ids.tracing: hash-1f7d0fe90187b06df4e180dd85bd17dfad60c4332cffafa0f9d3112268eb775e
- obj.clause-number: 5.1.3
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### tr--570aeb71-321d-47c4-82c1-10e363247405--FjK1SAzHxshj (provision)
Bei dezentralen Stromerzeugungsanlagen sind die Maßnahmen nach Tabelle 1 anzuwenden.
- bib.al.original-language: en
- bib.dp.publication-date: 2018-07-01
- ids.document: 7104561
- ids.element: section_5.1.3
- ids.language-synoptic: section_5.1.3
- ids.tracing: hash-471886b97b01996a376510fd0b1ea2c1b0521f627367134f5bb4c010954439b6
- obj.clause-number: 5.1.3
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-7104561-732b03c7ffc84bc

##### tr--570aeb71-321d-47c4-82c1-10e363247405--cPckAafPsulh (provision)
Die Einheiten der Gefahrenabwehr (z. B. Feuerwehr) setzen nur eigene ortsveränderliche elektrische Betriebsmittel (z. B. Tauchpumpen) ein, die den zu erwartenden Einsatzbedingungen genügen.
- bib.al.original-language: en
- bib.dp.publication-date: 2018-07-01
- ids.document: 7104561
- ids.element: section_5.1.3
- ids.language-synoptic: section_5.1.3
- ids.tracing: hash-430b7cdad477b974ba1929670db63cd9d65e8620587a8da9bcb06d68fade33d5
- obj.clause-number: 5.1.3
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### tr--570aeb71-321d-47c4-82c1-10e363247405--caTGMGIsyggh (provision)
Vorrangig sind für die Stromversorgung die eigenen Stromerzeuger einzusetzen.
- bib.al.original-language: en
- bib.dp.publication-date: 2018-07-01
- ids.document: 7104561
- ids.element: section_5.1.3
- ids.language-synoptic: section_5.1.3
- ids.tracing: hash-41370ce28a9dfa5d3ea492f98dd0985f1a1969497860cdc75b9fa44b9267694c
- obj.clause-number: 5.1.3
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### tr--570aeb71-321d-47c4-82c1-10e363247405--srWRFjZ7rOu7 (provision)
Sollte in Ausnahmefällen aufgrund der Einsatzsituation ein anderer Speisepunkt erforderlich sein, darf der Anschluss nur über eine Fehlerstromschutzeinrichtung des Typs SPE-PRCD für den Personenschutz erfolgen.
- bib.al.original-language: en
- bib.dp.publication-date: 2018-07-01
- ids.document: 7104561
- ids.element: section_5.1.3
- ids.language-synoptic: section_5.1.3
- ids.tracing: hash-ed7592d5868986e777a11dfb8613c9e6845338149de126888c1fe0a30e4163ce
- obj.clause-number: 5.1.3
- obj.element-name: paragraph
- obj.language: de
- obj.modality: permission
- obj.normativity: normative
- obj.specobject-type: provision
- use.business-process: undefined
- use.business-sector: undefined
- use.interaction: undefined
- use.location: undefined
- use.product-category: undefined
- use.product-life-cycle: undefined
- use.project-phase: undefined
- use.purpose: undefined

##### tr--570aeb71-321d-47c4-82c1-10e363247405--GpEtkUoBCyHL (provision)
Dieser ist möglichst nahe an der Stromentnahmestelle zu installieren.
- bib.al.original-language: en
- bib.dp.publication-date: 2018-07-01
- ids.document: 7104561
- ids.element: section_5.1.3
- ids.language-synoptic: section_5.1.3
- ids.tracing: hash-054ad0eeff2d6e8a9a93a59700a565e0e03f4b7581addebf686b0611e69e6d5c
- obj.clause-number: 5.1.3
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-6790a5f3967e4c9: 5.1.4 (heading)
- bib.al.original-language: en
- bib.dp.publication-date: 2018-07-01
- ids.document: 7104561
- ids.element: section_5.1.4
- ids.language-synoptic: section_5.1.4
- ids.tracing: hash-bc353035e614ccc60bff49605d798104216231f96be27656b9d29abc783205a8
- obj.element-name: heading
- obj.language: de
- obj.specobject-type: heading

##### tr--570aeb71-321d-47c4-82c1-10e363247405--HO34sbZeQKMk (provision)
Bei Bränden und technischer Hilfeleistung in elektrischen Anlagen (Elektrizitätsversorgungsnetzen und/oder dezentrale Stromversorgungsanlagen) oder in deren Nähe sind, soweit überhaupt eine Notwendigkeit dazu vorliegt, nur die betroffenen oder unmittelbar bedrohten Teile spannungsfrei zu schalten.
- bib.al.original-language: en
- bib.dp.publication-date: 2018-07-01
- ids.document: 7104561
- ids.element: section_5.1.4
- ids.language-synoptic: section_5.1.4
- ids.tracing: hash-a31e67b73889637cfa0d7ba9c71be8382c4f7bc9fdf0d4107d197f5e7653acaa
- obj.clause-number: 5.1.4
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### tr--570aeb71-321d-47c4-82c1-10e363247405--YxoynwVqM7u5 (provision)
Einige Stromversorgungsanlagen können systembedingt nicht spannungsfrei geschaltet werden (siehe Tabelle 1).
- bib.al.original-language: en
- bib.dp.publication-date: 2018-07-01
- ids.document: 7104561
- ids.element: section_5.1.4
- ids.language-synoptic: section_5.1.4
- ids.tracing: hash-85d892ee4fe13a6a4550817cdb7453c177bc21e4cc70b695c75ca01e3cac3d89
- obj.clause-number: 5.1.4
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-7104561-732b03c7ffc84bc

##### tr--570aeb71-321d-47c4-82c1-10e363247405--fiE3T6RTp6Qr (provision)
Grundsatz muss sein, dass so wenig wie möglich ausgeschaltet wird.
- bib.al.original-language: en
- bib.dp.publication-date: 2018-07-01
- ids.document: 7104561
- ids.element: section_5.1.4
- ids.language-synoptic: section_5.1.4
- ids.tracing: hash-e3255aa67756a4a48631b90a83a2b4eafe148fa602f3957082e4030ff0ebd62a
- obj.clause-number: 5.1.4
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### tr--570aeb71-321d-47c4-82c1-10e363247405--aVJeinf97NLz (provision)
Mit Rücksicht auf die Nachteile für die Brandbekämpfung und bei technischer Hilfeleistung sowie für die Allgemeinheit sind Abschaltungen nur in Absprache zwischen Feuerwehr und dem Anlagenbetreiber vorzunehmen.
- bib.al.original-language: en
- bib.dp.publication-date: 2018-07-01
- ids.document: 7104561
- ids.element: section_5.1.4
- ids.language-synoptic: section_5.1.4
- ids.tracing: hash-d753ebcda6ad0f9ae42b07115cc9f9935c885d805ef47a2cccdd2f56e7a17d0e
- obj.clause-number: 5.1.4
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### prov-7104561-82a096555713422: , Note (provision)
ANMERKUNG 1:
Dadurch soll z. B. vermieden werden:
- bib.al.original-language: en
- bib.dp.publication-date: 2018-07-01
- ids.document: 7104561
- ids.element: section_5.1.4
- ids.language-synoptic: section_5.1.4
- ids.tracing: hash-f64699d422245c3d11de92de4aa0353e6579eea6117a32e6cf7a224b6a65d71a
- obj.clause-number: 5.1.4
- obj.element-name: note
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

##### prov-7104561-9cc1db937ecd471 (provision)
- Gefährdung von Patienten;
- Stilllegen der Wasserversorgung;
- Gefährdungen und Schäden durch die Unterbrechung von Betriebsabläufen;
- Stillstand von Aufzügen und elektrisch betätigten Toren;
- Verdunklung von Straßen.
- bib.al.original-language: en
- bib.dp.publication-date: 2018-07-01
- ids.document: 7104561
- ids.element: section_5.1.4
- ids.language-synoptic: section_5.1.4
- ids.tracing: hash-fef7c18e2692fdfe5706662577340ea1b29ffc60ef76d3cba1a231c2bcab4e3d
- obj.clause-number: 5.1.4
- obj.element-name: unordered-list
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### prov-7104561-d8c93b3671de45a: , Note (provision)
ANMERKUNG 2 Lichtbögen können im Allgemeinen nur durch Ausschalten unterbrochen werden.
- bib.al.original-language: en
- bib.dp.publication-date: 2018-07-01
- ids.document: 7104561
- ids.element: section_5.1.4
- ids.language-synoptic: section_5.1.4
- ids.tracing: hash-50ccd56c4133795adf120d90534d1d336e4ef35379c925041bba9133095749e4
- obj.clause-number: 5.1.4
- obj.element-name: note
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

##### prov-7104561-0fa1c925bc364f4: , Note (provision)
ANMERKUNG 3 Die Benutzung von Aufzügen – mit Ausnahme von Feuerwehraufzügen – ist wegen der Gefahr eines Stromausfalls gefährlich und zu vermeiden.
- bib.al.original-language: en
- bib.dp.publication-date: 2018-07-01
- ids.document: 7104561
- ids.element: section_5.1.4
- ids.language-synoptic: section_5.1.4
- ids.tracing: hash-02ec52dfdb1922d5f8d3c3c36dd262086e40123837cb41ccca9ab31cdfd8c0b4
- obj.clause-number: 5.1.4
- obj.element-name: note
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

##### tr--570aeb71-321d-47c4-82c1-10e363247405--cJl0SRgLDnmf (provision)
Anlagen, die dem Brandschutz und der Brandbekämpfung dienen (z. B. Rauch- und Wärmeabzugsanlagen, Sprinkler- und Sprühwasserlöschanlagen), dürfen ohne zwingende Notwendigkeit nicht außer Betrieb gesetzt werden.
- bib.al.original-language: en
- bib.dp.publication-date: 2018-07-01
- ids.document: 7104561
- ids.element: section_5.1.4
- ids.language-synoptic: section_5.1.4
- ids.tracing: hash-3e7f9dac5fd1d684ded2f10a2a4a308f779c8656a093ba19680c0cae2c3d67d1
- obj.clause-number: 5.1.4
- obj.element-name: paragraph
- obj.language: de
- obj.modality: permission
- obj.normativity: normative
- obj.specobject-type: provision
- use.business-process: undefined
- use.business-sector: undefined
- use.interaction: undefined
- use.location: undefined
- use.product-category: undefined
- use.product-life-cycle: undefined
- use.project-phase: undefined
- use.purpose: undefined

##### tr--570aeb71-321d-47c4-82c1-10e363247405--EqpMV86J54jM (provision)
Durch Schalten elektrischer Betriebsmittel können erhöhte Brand- und Explosionsgefahren auftreten.
- bib.al.original-language: en
- bib.dp.publication-date: 2018-07-01
- ids.document: 7104561
- ids.element: section_5.1.4
- ids.language-synoptic: section_5.1.4
- ids.tracing: hash-08a2eaff70873b25ccba9bf7388298bc024db58ed19608d033da28761740e2d8
- obj.clause-number: 5.1.4
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### prov-7104561-732b03c7ffc84bc: Besonderheiten bei dezentralen Stromerzeugungsanlagen oder anderen Energiesystemen (provision)
Tabelle 1 — Besonderheiten bei dezentralen Stromerzeugungsanlagen oder anderen Energiesystemen
Brandbekämpfung und technische Hilfeleistung sind grundsätzlich möglich, wenn die Abstände nach den Tabellen 2 bis 8 eingehalten werden. Darüber hinaus sind nachstehende Maßnahmen hilfreich.
| Energiesystem | Maßnahme | Restgefährdung | Anmerkung |
| --- | --- | --- | --- |
| 1. PV-Anlage | – | Selbst bei durch eine Elektrofachkraft festgestellter Spannungsfreiheit können beim Trennen von Leitungen/Steckverbindern Lichtbögen entstehen. | Trotz Abschaltungen kann nicht von einer vollständigen Spannungsfreiheit der PV-Anlage ausgegangen werden. Daher gilt der Grundsatz Abstand halten. Durch Mondlicht oder künstliches Licht (Scheinwerfer) tritt keine elektrische Gefährdung auf (siehe auch Anhang B „Erläuterungen“). |
| - 2) 2) Elektro- und Hybridfahrzeuge | Deaktivieren des Hochvoltsystems (falls das Rückhaltesystem (z. B. Airbag) ausgelöst hat, ist dies in der Regel sichergestellt). 1. Abklemmen der 12 V/24 V-Batterie oder 2. HV-Wartungsschalter (Service Disconnect) betätigen oder 3. fahrzeugspezifische Trennvorrichtungen betätigen. | Siehe 5.1.5 Besondere Maßnahmen bei Lithium-Ionen-Akkumulatoren. . | Brände können mit Wasser gelöscht werden. Sollten Personen durch technische Hilfeleistung aus dem Fahrzeug zu befreien sein, ist davon auszugehen, dass das Rückhaltesystem ausgelöst hat und das HV-System deaktiviert wurde. HV-Kabel sind orange. HV-Komponenten sind durch das Bildzeichen 5036 nach IEC 60417-DB:2002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 gekennzeichnet. |
| - 3) 3) Batterieanlage (z. B. Sicherheitsstromversorgung, USV-Anlage) | Unter Last dürfen - Sicherungen nicht gezogen und - Kabel/Leitungen nicht gelöst oder getrennt werden. | Spannung bleibt in der eigentlichen Batterieanlage bis zur ersten Abschalt-/ Trennein-richtung bestehen; Gefährdung durch Lichtbogen bei Kurzschluss oder beim Abschalten. | Das Abschalten der Batterie ist nicht möglich. Die von der Batterie versorgte elektrische Anlage kann jedoch in der Regel freigeschaltet werden. |
| - 4) 4) Stromerzeugungsaggregat | Not-Ausschalter betätigen oder Stromerzeuger ausschalten. Zusätzlich Brennstoffzufuhr unterbrechen. | Spannung steht noch bis zum Stillstand des Aggregats an. | – |
| - 5) 5) Brennstoffzellenanlage | Not-Ausschalter betätigen. Zusätzlich Brennstoffzufuhr unterbrechen. | Spannung kann nach Unterbrechen der Brennstoffzufuhr weiter anstehen. | Die Dauer der Restgefährdung ist abhängig von dem dann noch zur Verfügung stehenden Restbrennstoff. |
| - 6) 6) Windenergieanlage | Sicherung der Einsatzstelle, dabei Bauhöhe, Windrichtung und Windstärke berücksichtigen. | Einsturzgefahr, Gefährdung durch wegfliegende Trümmer, Brandausbreitung. | Gegebenenfalls kontrolliert abbrennen lassen. |
- bib.al.original-language: en
- bib.dp.publication-date: 2018-07-01
- ids.document: 7104561
- ids.element: table_1
- ids.language-synoptic: table_1
- ids.tracing: hash-21ea362db31e4db56a2a7d73e628bc1498df736db3788d305280a0e7fa87e1c3
- obj.clause-number: Tabelle 1
- obj.element-name: table
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-7104561-b2af74b355cb46d
- cross-reference -> prov-7104561-f118db89e55047b
- cross-reference -> prov-7104561-de920128e095448

#### prov-7104561-de920128e095448: Besondere Maßnahmen bei Lithium-Ionen-Akkumulatoren (heading)
- bib.al.original-language: en
- bib.dp.publication-date: 2018-07-01
- ids.document: 7104561
- ids.element: section_5.1.5
- ids.language-synoptic: section_5.1.5
- ids.tracing: hash-6712415e597a3a7558918bb6c44a4fa8cc21598c8e781bc438a1b2f53fd4267e
- obj.clause-number: 5.1.5
- obj.element-name: heading
- obj.language: de
- obj.specobject-type: heading
- ChapterName: 5.1.5 Besondere Maßnahmen bei Lithium-Ionen-Akkumulatoren

##### prov-7104561-5d9e208f8a07407: Allgemeines (heading)
- bib.al.original-language: en
- bib.dp.publication-date: 2018-07-01
- ids.document: 7104561
- ids.element: section_5.1.5.1
- ids.language-synoptic: section_5.1.5.1
- ids.tracing: hash-77fa9898e9c4b1155590161ec2b4a8eaf702a3e24b23bf812e87ce6a2dc50013
- obj.clause-number: 5.1.5.1
- obj.element-name: heading
- obj.language: de
- obj.specobject-type: heading
- ChapterName: 5.1.5.1 Allgemeines

###### tr--570aeb71-321d-47c4-82c1-10e363247405--IjuivEGiwY2a: Allgemeines (provision)
Lithium-Ionen-Akkumulatoren sind vor allem anzutreffen:
- bei elektromobilen Anwendungen (z. B. Elektro- und Hybrid-Fahrzeugen, Pedelecs);
- in stationären Speichern (z. B. Haushaltsspeichern in Verbindung mit PV-Anlagen, Quartierspeichern und Großspeichern der Netzbetreiber);
- in Lagerstätten (z. B. Produktion, Handel, Entsorgung).
- bib.al.original-language: en
- bib.dp.publication-date: 2018-07-01
- ids.document: 7104561
- ids.element: section_5.1.5.1
- ids.language-synoptic: section_5.1.5.1
- ids.tracing: hash-e6dd92b9fca397e2c41b2ccb8f4df70013455d6041863dd12235560437b2d96b
- obj.clause-number: 5.1.5.1
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### prov-7104561-433e5d21fa5b40d: Gefährdungen (heading)
- bib.al.original-language: en
- bib.dp.publication-date: 2018-07-01
- ids.document: 7104561
- ids.element: section_5.1.5.2
- ids.language-synoptic: section_5.1.5.2
- ids.tracing: hash-d5afb7cbdb913765fb767fee936b3d94303a400d01dcbab577a179b19a9c19ca
- obj.clause-number: 5.1.5.2
- obj.element-name: heading
- obj.language: de
- obj.specobject-type: heading
- ChapterName: 5.1.5.2 Gefährdungen

###### tr--570aeb71-321d-47c4-82c1-10e363247405--IwbtfKhvs35m: Gefährdungen (provision)
Folgende Gefährdungen können von Lithium-Ionen-Akkumulatoren ausgehen:
- elektrische (z. B. Rückspannung in die Elektroinstallation trotz Trennung vom örtlichen Stromversorgungsnetz);
- thermische (z. B. extreme Brandausbreitung);
- chemische (z. B. Flusssäure, giftige und brennbare Gase).
- bib.al.original-language: en
- bib.dp.publication-date: 2018-07-01
- ids.document: 7104561
- ids.element: section_5.1.5.2
- ids.language-synoptic: section_5.1.5.2
- ids.tracing: hash-93c09022768028cde328e41322f9824dbcedf046f096031072eb8ae10ed3aa9d
- obj.clause-number: 5.1.5.2
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

###### tr--570aeb71-321d-47c4-82c1-10e363247405--Ou5zwAhmAWQB: Gefährdungen (provision)
Diese vorstehend genannten Gefährdungen können auch zeitverzögert bis zu mehrere Stunden nach einer Schadenseinwirkung auftreten.
- bib.al.original-language: en
- bib.dp.publication-date: 2018-07-01
- ids.document: 7104561
- ids.element: section_5.1.5.2
- ids.language-synoptic: section_5.1.5.2
- ids.tracing: hash-07ba18540b6df6722d82a50b8123706d91c7e22174e71cc60b733e7c6ebe661c
- obj.clause-number: 5.1.5.2
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

###### tr--570aeb71-321d-47c4-82c1-10e363247405--r0jCx6xe9iXT: Gefährdungen (provision)
Auslöser eines Schadensereignisses können z. B. sein: Blitzeinschlag, Überspannung, Überschwemmung, Brand, mechanische Einwirkung.
- bib.al.original-language: en
- bib.dp.publication-date: 2018-07-01
- ids.document: 7104561
- ids.element: section_5.1.5.2
- ids.language-synoptic: section_5.1.5.2
- ids.tracing: hash-2f58de303e960443a26f472e2cf093253bd97c729c7d2c5cb8fcd53f7a8a2c80
- obj.clause-number: 5.1.5.2
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### prov-7104561-f0063afaf0e1452: Maßnahmen (heading)
- bib.al.original-language: en
- bib.dp.publication-date: 2018-07-01
- ids.document: 7104561
- ids.element: section_5.1.5.3
- ids.language-synoptic: section_5.1.5.3
- ids.tracing: hash-15ca7031bcd6316debd4c069872d659736a31c076e8ad525019a207e5b55010f
- obj.clause-number: 5.1.5.3
- obj.element-name: heading
- obj.language: de
- obj.specobject-type: heading
- ChapterName: 5.1.5.3 Maßnahmen

###### tr--570aeb71-321d-47c4-82c1-10e363247405--mxaS3bGI0piZ: Maßnahmen (provision)
Nur die benötigten Einsatzkräfte dürfen den unmittelbaren Gefahrenbereich (in der Regel den betroffenen Raum) betreten.
- bib.al.original-language: en
- bib.dp.publication-date: 2018-07-01
- ids.document: 7104561
- ids.element: section_5.1.5.3
- ids.language-synoptic: section_5.1.5.3
- ids.tracing: hash-770f7aa335e3e6a5484c1d1f55df780e01e9ed06de9ca70dc5f4ddc5b3e87118
- obj.clause-number: 5.1.5.3
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

###### tr--570aeb71-321d-47c4-82c1-10e363247405--GUKK3VeadTkI: Maßnahmen (provision)
Dabei sollten diese Einsatzkräfte den größtmöglichen Abstand halten bzw. aufgrund der extremen Brandausbreitung aus der Deckung arbeiten.
- bib.al.original-language: en
- bib.dp.publication-date: 2018-07-01
- ids.document: 7104561
- ids.element: section_5.1.5.3
- ids.language-synoptic: section_5.1.5.3
- ids.tracing: hash-9e68dbf9a69f64651ed4a23cbbc1417efc85103cfb5be32e09ccc6a248ba6053
- obj.clause-number: 5.1.5.3
- obj.element-name: paragraph
- obj.language: de
- obj.modality: recommendation
- obj.normativity: normative
- obj.specobject-type: provision
- use.business-process: undefined
- use.business-sector: undefined
- use.interaction: undefined
- use.location: undefined
- use.product-category: undefined
- use.product-life-cycle: undefined
- use.project-phase: undefined
- use.purpose: undefined

###### tr--570aeb71-321d-47c4-82c1-10e363247405--dKfsOM8COKhG: Maßnahmen (provision)
Bei Verdacht auf beschädigte Lithium-Ionen-Akkumulatoren ist der Anlagenbetreiber über das Risiko der verzögerten Reaktion und des weiteren Betriebes zu informieren, damit er die sofortige Stilllegung und einen zeitnahen Ausbau des Lithium-Ionen-Akkumulators veranlassen kann.
- bib.al.original-language: en
- bib.dp.publication-date: 2018-07-01
- ids.document: 7104561
- ids.element: section_5.1.5.3
- ids.language-synoptic: section_5.1.5.3
- ids.tracing: hash-3a9926f7c5e37613bcd341d0a36ad463cfb7ee84f782386dca140f463ca4556a
- obj.clause-number: 5.1.5.3
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

###### tr--570aeb71-321d-47c4-82c1-10e363247405--SdCERn1LRAdI: Maßnahmen (provision)
Beim Einsatz können Personen und Geräte in Kontakt kommen mit:
- Elektrolyt oder
- Zersetzungsprodukten (u. a. Flusssäure in kontaminiertem Löschmittel).
- bib.al.original-language: en
- bib.dp.publication-date: 2018-07-01
- ids.document: 7104561
- ids.element: section_5.1.5.3
- ids.language-synoptic: section_5.1.5.3
- ids.tracing: hash-fd33e1f22679004fd7c41649702dbe6b52b5e327b4c02af3c63f227b1e7b38ef
- obj.clause-number: 5.1.5.3
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

###### tr--570aeb71-321d-47c4-82c1-10e363247405--pKbxLDcxvPcP: Maßnahmen (provision)
Für diesen Fall sind Maßnahmen nach der Feuerwehrdienstvorschrift 500 „Einheiten im ABC-Einsatz“ zu ergreifen.
- bib.al.original-language: en
- bib.dp.publication-date: 2018-07-01
- ids.document: 7104561
- ids.element: section_5.1.5.3
- ids.language-synoptic: section_5.1.5.3
- ids.tracing: hash-281b0ff001a17eb4bcad07bb325ad911143a4ae912afb2450ed24b70e71e9dad
- obj.clause-number: 5.1.5.3
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

###### prov-7104561-70beb7d4960f4ca: Maßnahmen (provision)
1. Brennende Lithium-Ionen-Akkumulatoren.
- bib.al.original-language: en
- bib.dp.publication-date: 2018-07-01
- ids.document: 7104561
- ids.element: section_5.1.5.3
- ids.language-synoptic: section_5.1.5.3
- ids.tracing: hash-a8c0ef5b46aa2f2a2919834b34a7d9f790ff9ad1d61874c2c525ef34d3bb9732
- obj.clause-number: 5.1.5.3
- obj.element-name: ordered-list
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

###### tr--570aeb71-321d-47c4-82c1-10e363247405--Xa2hnV5Xm5DV: Maßnahmen (provision)
Wasser ist aufgrund der Kühlwirkung als Löschmittel zu empfehlen.
- bib.al.original-language: en
- bib.dp.publication-date: 2018-07-01
- ids.document: 7104561
- ids.element: section_5.1.5.3
- ids.language-synoptic: section_5.1.5.3
- ids.tracing: hash-52a4707685b8f81c361977fd7b559fc3165765777b69b3496699fda991bf883f
- obj.clause-number: 5.1.5.3
- obj.element-name: paragraph
- obj.language: de
- obj.modality: recommendation
- obj.normativity: normative
- obj.specobject-type: provision
- use.business-process: undefined
- use.business-sector: undefined
- use.interaction: undefined
- use.location: undefined
- use.product-category: undefined
- use.product-life-cycle: undefined
- use.project-phase: undefined
- use.purpose: undefined

###### tr--570aeb71-321d-47c4-82c1-10e363247405--h7oL4rpZe2hR: Maßnahmen (provision)
Brennende Lithium-Ionen-Akkumulatoren sind nur schwer zu löschen.
- bib.al.original-language: en
- bib.dp.publication-date: 2018-07-01
- ids.document: 7104561
- ids.element: section_5.1.5.3
- ids.language-synoptic: section_5.1.5.3
- ids.tracing: hash-874e6f5a1b333cc14ecddacb36ea79428278c652e99951dc09bf44a0950e4dfa
- obj.clause-number: 5.1.5.3
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

###### tr--570aeb71-321d-47c4-82c1-10e363247405--VNvfhzCirzoX: Maßnahmen (provision)
Daher liegt das taktische Ziel der Einsatzmaßnahme auf der Verhinderung einer weiteren Brandausbreitung.
- bib.al.original-language: en
- bib.dp.publication-date: 2018-07-01
- ids.document: 7104561
- ids.element: section_5.1.5.3
- ids.language-synoptic: section_5.1.5.3
- ids.tracing: hash-dba69c694b5bbb9bf3664d9560115c9abd264880406948c95b28d1a7bd91f4f7
- obj.clause-number: 5.1.5.3
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

###### tr--570aeb71-321d-47c4-82c1-10e363247405--HMJx53T6lEnU: Maßnahmen (provision)
Bei Lagerstätten mit Lithium-Ionen-Akkumulatoren sind ggf. Maßnahmen zur Löschwasserrückhaltung erforderlich.
- bib.al.original-language: en
- bib.dp.publication-date: 2018-07-01
- ids.document: 7104561
- ids.element: section_5.1.5.3
- ids.language-synoptic: section_5.1.5.3
- ids.tracing: hash-924b2eb89a3f1ffdc4b66e99c73afd339e431194726f6ff227568ab380f75726
- obj.clause-number: 5.1.5.3
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

###### prov-7104561-ebfea2dcc8874e4: Maßnahmen (provision)
- 2)
2) Vermeiden des Entzündens der Lithium-Ionen-Akkumulatoren.
- bib.al.original-language: en
- bib.dp.publication-date: 2018-07-01
- ids.document: 7104561
- ids.element: section_5.1.5.3
- ids.language-synoptic: section_5.1.5.3
- ids.tracing: hash-56adb5eb9c1722889a052f45f045acdcee1213502e61037c533822513e6a1726
- obj.clause-number: 5.1.5.3
- obj.element-name: ordered-list
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

###### tr--570aeb71-321d-47c4-82c1-10e363247405--zG0N4qy0MwZ5: Maßnahmen (provision)
Bei oder nach thermischer Einwirkung von außen (Akkumulatortemperatur ab etwa 80 °C) sollte der Lithium-Ionen-Akkumulator gekühlt werden, um sein Entzünden und/oder eine Gasfreisetzung zu verhindern (z. B. bei einem Zimmerbrand).
- bib.al.original-language: en
- bib.dp.publication-date: 2018-07-01
- ids.document: 7104561
- ids.element: section_5.1.5.3
- ids.language-synoptic: section_5.1.5.3
- ids.tracing: hash-8cbce6e13ec6e11461c9893a50298f98f3431fded357071abf8687ae240974d8
- obj.clause-number: 5.1.5.3
- obj.element-name: paragraph
- obj.language: de
- obj.modality: recommendation
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-583463d498a24cc: 5.1.6 (heading)
- bib.al.original-language: en
- bib.dp.publication-date: 2018-07-01
- ids.document: 7104561
- ids.element: section_5.1.6
- ids.language-synoptic: section_5.1.6
- ids.tracing: hash-7f082b1833b539b8a52315edcfd96c981a3a4d4e5ec89cb7e871e6fa4d10aa4d
- obj.element-name: heading
- obj.language: de
- obj.specobject-type: heading

##### tr--570aeb71-321d-47c4-82c1-10e363247405--PBcn66QKcSoN (provision)
Beim Einsatz von Leitern, Teleskopmasten und anderen Geräten dürfen die unter 5.2.4, 5.3.4 und 5.3.5 angegebenen und jeweils zutreffenden Mindestabstände nicht unterschritten werden.
- bib.al.original-language: en
- bib.dp.publication-date: 2018-07-01
- ids.document: 7104561
- ids.element: section_5.1.6
- ids.language-synoptic: section_5.1.6
- ids.tracing: hash-e6e8d56ebf78bbf26c39019e26ec3908bb06bda619b2bd49a85dff9866e584a3
- obj.clause-number: 5.1.6
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-7104561-1cfccb0263ba433
- cross-reference -> prov-7104561-24000de83ed8423
- cross-reference -> prov-7104561-80f799700b314a0

##### tr--570aeb71-321d-47c4-82c1-10e363247405--aB892KKwojxU (provision)
Hierbei ist die Annäherung durch Belastungen und Schwankungen zu berücksichtigen.
- bib.al.original-language: en
- bib.dp.publication-date: 2018-07-01
- ids.document: 7104561
- ids.element: section_5.1.6
- ids.language-synoptic: section_5.1.6
- ids.tracing: hash-930674d826e9dd733fa5cb6a6f3ef1966164afeb53d407fcb3a8aa4b9a42fd25
- obj.clause-number: 5.1.6
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-b3fe32a1dc1c4f9: 5.1.7 (heading)
- bib.al.original-language: en
- bib.dp.publication-date: 2018-07-01
- ids.document: 7104561
- ids.element: section_5.1.7
- ids.language-synoptic: section_5.1.7
- ids.tracing: hash-1d07b27f5ca5ad4b5b5aef9f8ae58f5dc1a410e98db2abda3793fb5d614c1580
- obj.element-name: heading
- obj.language: de
- obj.specobject-type: heading

##### tr--570aeb71-321d-47c4-82c1-10e363247405--o9QgFJ9rLd4P (provision)
Nicht vom Brand betroffene elektrische Maschinen, Schalttafeln, Geräte, Fernmeldeanlagen usw. sind nach Möglichkeit vor Löschmitteln zu schützen.
- bib.al.original-language: en
- bib.dp.publication-date: 2018-07-01
- ids.document: 7104561
- ids.element: section_5.1.7
- ids.language-synoptic: section_5.1.7
- ids.tracing: hash-ae46a5795c927390900e05dc5b69bac2968325152133b863ac8e9275c2b9115c
- obj.clause-number: 5.1.7
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-53fd219c9b90450: 5.1.8 (heading)
- bib.al.original-language: en
- bib.dp.publication-date: 2018-07-01
- ids.document: 7104561
- ids.element: section_5.1.8
- ids.language-synoptic: section_5.1.8
- ids.tracing: hash-221436dc3df2cffaa1a37b6ae2cffc17db47d0a734c4cc340cc10ee211c2011d
- obj.element-name: heading
- obj.language: de
- obj.specobject-type: heading

##### tr--570aeb71-321d-47c4-82c1-10e363247405--q5zxgnmtx6HI (provision)
Klimaanlagen, Lüftungsanlagen usw. sind so zu steuern, dass eine Ausbreitung von Brandrauch im Gebäude vermieden wird.
- bib.al.original-language: en
- bib.dp.publication-date: 2018-07-01
- ids.document: 7104561
- ids.element: section_5.1.8
- ids.language-synoptic: section_5.1.8
- ids.tracing: hash-4fc81ac7168f6eeb5676939f879c54097bacae560dab686487ec6bc02c7a49be
- obj.clause-number: 5.1.8
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-ca33f936afd24cc: Besondere Maßnahmen für Niederspannungsanlagen (heading)
- bib.al.original-language: en
- bib.dp.publication-date: 2018-07-01
- ids.document: 7104561
- ids.element: section_5.2
- ids.language-synoptic: section_5.2
- ids.tracing: hash-6d77a885cafe5e18cf8565abe385f00c2fd55fd657e265bce4619305d58866f7
- obj.clause-number: 5.2
- obj.element-name: heading
- obj.language: de
- obj.specobject-type: heading
- ChapterName: 5.2 Besondere Maßnahmen für Niederspannungsanlagen

#### prov-7104561-7f80523feb704e7: 5.2.1 (heading)
- bib.al.original-language: en
- bib.dp.publication-date: 2018-07-01
- ids.document: 7104561
- ids.element: section_5.2.1
- ids.language-synoptic: section_5.2.1
- ids.tracing: hash-5a12bbd848e6733ab0ed3ff5c884968a05150d5c315f9e302bbc8287aaf710f9
- obj.element-name: heading
- obj.language: de
- obj.specobject-type: heading

##### tr--570aeb71-321d-47c4-82c1-10e363247405--k3S4gRHRTWKr (provision)
Sind im Bereich der Einsatzstelle umfangreiche Zerstörungen der Niederspannungsanlagen, insbesondere der Freileitungen, zu erwarten oder bereits eingetreten, so sind die betroffenen Leitungen im Bereich der Einsatzstelle spannungsfrei zu machen [siehe DIN VDE 0105-100 (VDE 0105-100):2015-10, 6.2] .
- bib.al.original-language: en
- bib.dp.publication-date: 2018-07-01
- ids.document: 7104561
- ids.element: section_5.2.1
- ids.language-synoptic: section_5.2.1
- ids.tracing: hash-582d253abd4451c313bf08b9154f6278c845aba385129b5997b346fd185eccd9
- obj.clause-number: 5.2.1
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### prov-7104561-1c816b4c335f450: , Note (provision)
ANMERKUNG:
Diese Maßnahme ist erforderlich, weil der Isolationszustand, z. B. durch Brandeinwirkung oder Löschmaßnahmen unter Umständen erheblich herabgesetzt werden kann, und weil Freileitungen reißen können.
- bib.al.original-language: en
- bib.dp.publication-date: 2018-07-01
- ids.document: 7104561
- ids.element: section_5.2.1
- ids.language-synoptic: section_5.2.1
- ids.tracing: hash-e6cba068cb024ea4a9e3a99fbb9b1e7d55a0b9cc5216244e85314d47fdbe87b2
- obj.clause-number: 5.2.1
- obj.element-name: note
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

##### tr--570aeb71-321d-47c4-82c1-10e363247405--CxJV1ycVjRxF (provision)
Eine Berührung von herabgefallenen Leitungen, auch wenn sie am Boden liegen, und eine Berührung der im normalen Zustand nicht unter Spannung stehenden Metallteile, z. B. Maschinen, Fernmelde-Freileitungen, Antennen, Blechdächer und -wände, Regenrinnen, Wasser- oder Gasleitungen, Metallzäune, kann gefährlich sein.
- bib.al.original-language: en
- bib.dp.publication-date: 2018-07-01
- ids.document: 7104561
- ids.element: section_5.2.1
- ids.language-synoptic: section_5.2.1
- ids.tracing: hash-3767106f191aa0dbe308322201a9e9a2b2bbd7afc801cdd6913ccb06ef1d4ee9
- obj.clause-number: 5.2.1
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### tr--570aeb71-321d-47c4-82c1-10e363247405--Qli4HKZIffSF (provision)
Diese Metallteile können unter Umständen unter Spannung stehen.
- bib.al.original-language: en
- bib.dp.publication-date: 2018-07-01
- ids.document: 7104561
- ids.element: section_5.2.1
- ids.language-synoptic: section_5.2.1
- ids.tracing: hash-cc5edea638d0393a6126310c452fa91ce90fafaa3d30b51dc67f601d05b666ce
- obj.clause-number: 5.2.1
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-95081d6608e1477: 5.2.2 (heading)
- bib.al.original-language: en
- bib.dp.publication-date: 2018-07-01
- ids.document: 7104561
- ids.element: section_5.2.2
- ids.language-synoptic: section_5.2.2
- ids.tracing: hash-7088cef944f25a3221a3e1fa262f163b8eabeb2255ae04de0422b13067241d37
- obj.element-name: heading
- obj.language: de
- obj.specobject-type: heading

##### tr--570aeb71-321d-47c4-82c1-10e363247405--UcaPBJAgDt9d (provision)
Schalthandlungen in Niederspannungsanlagen dürfen nur von Elektrofachkräften oder elektrotechnisch unterwiesenen Personen vorgenommen werden.
- bib.al.original-language: en
- bib.dp.publication-date: 2018-07-01
- ids.document: 7104561
- ids.element: section_5.2.2
- ids.language-synoptic: section_5.2.2
- ids.tracing: hash-4fd471ac2fa1787ed73ffd663c4943442e0626f70f33d13425a2c29df723a94b
- obj.clause-number: 5.2.2
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### tr--570aeb71-321d-47c4-82c1-10e363247405--cv2DVWGQLZVF (provision)
Hiervon ausgenommen sind Hausinstallationen.
- bib.al.original-language: en
- bib.dp.publication-date: 2018-07-01
- ids.document: 7104561
- ids.element: section_5.2.2
- ids.language-synoptic: section_5.2.2
- ids.tracing: hash-7ee73994c4915f8a833c0aea84f6b96a5beca12ec8e3435b1cc750f25fd67b47
- obj.clause-number: 5.2.2
- obj.element-name: paragraph
- obj.language: de
- obj.modality: permission
- obj.normativity: normative
- obj.specobject-type: provision
- use.business-process: undefined
- use.business-sector: undefined
- use.interaction: undefined
- use.location: undefined
- use.product-category: undefined
- use.product-life-cycle: undefined
- use.project-phase: undefined
- use.purpose: undefined

##### prov-7104561-c429b9b17d444f9: , Note (provision)
ANMERKUNG:
Zur Hausinstallation im Sinne dieser Norm gehören auch elektromedizinische Geräte, Leuchtröhrenanlagen, z. B. für Reklame, die zwar mit Hochspannung betrieben werden, jedoch an die Hausinstallation angeschlossen sind und dort geschaltet werden können.
- bib.al.original-language: en
- bib.dp.publication-date: 2018-07-01
- ids.document: 7104561
- ids.element: section_5.2.2
- ids.language-synoptic: section_5.2.2
- ids.tracing: hash-36a5aa0e27516286212b104846bb9235252de54b46a195dbe3a4cf6c40a73b7b
- obj.clause-number: 5.2.2
- obj.element-name: note
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

#### prov-7104561-9f913abd6298414: 5.2.3 (heading)
- bib.al.original-language: en
- bib.dp.publication-date: 2018-07-01
- ids.document: 7104561
- ids.element: section_5.2.3
- ids.language-synoptic: section_5.2.3
- ids.tracing: hash-7f2976012b023ff451b183bd0edf894be8a724fd4f1865083bf92e216d25f943
- obj.element-name: heading
- obj.language: de
- obj.specobject-type: heading

##### tr--570aeb71-321d-47c4-82c1-10e363247405--8bmUKgwwj8V7 (provision)
Unsachgemäßes Kurzschließen oder Durchtrennen von unter Spannung stehenden Leitungen und Kabeln ist lebensgefährlich.
- bib.al.original-language: en
- bib.dp.publication-date: 2018-07-01
- ids.document: 7104561
- ids.element: section_5.2.3
- ids.language-synoptic: section_5.2.3
- ids.tracing: hash-aecd34cfdf962c2eeacdb12fc327a13e2182a808b8c17faf7ee6f2eb2037d50c
- obj.clause-number: 5.2.3
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### tr--570aeb71-321d-47c4-82c1-10e363247405--HoZY2DnhlLUc (provision)
Kurzschließen oder Durchtrennen von unter Spannung stehenden Leitungen und Kabeln als Notmaßnahme darf daher nur bei Gefährdung von Menschenleben und nur von Elektrofachkräften durchgeführt werden.
- bib.al.original-language: en
- bib.dp.publication-date: 2018-07-01
- ids.document: 7104561
- ids.element: section_5.2.3
- ids.language-synoptic: section_5.2.3
- ids.tracing: hash-5e1bc467c540873655e37944d0268a493a7cd4a5f16e1094dab6c32f0ad2dc8c
- obj.clause-number: 5.2.3
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-1cfccb0263ba433: 5.2.4 (heading)
- bib.al.original-language: en
- bib.dp.publication-date: 2018-07-01
- ids.document: 7104561
- ids.element: section_5.2.4
- ids.language-synoptic: section_5.2.4
- ids.tracing: hash-28ae4927b8b0e3661be88a5b3f84a241673f65f1ea3009011f71c506d03479eb
- obj.element-name: heading
- obj.language: de
- obj.specobject-type: heading

##### tr--570aeb71-321d-47c4-82c1-10e363247405--VLav1qR3jT09 (provision)
Bei Annäherung (z. B. beim Erkunden und Retten) an unter Spannung stehende Niederspannungsanlagenteile ist der Mindestabstand nach Tabelle 2 einzuhalten.
- bib.al.original-language: en
- bib.dp.publication-date: 2018-07-01
- ids.document: 7104561
- ids.element: section_5.2.4
- ids.language-synoptic: section_5.2.4
- ids.tracing: hash-d3ab28877c2a7f3b5efbcad843573427927539773a10e5e3a7855f03760248b3
- obj.clause-number: 5.2.4
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-7104561-b2af74b355cb46d

##### tr--570aeb71-321d-47c4-82c1-10e363247405--mqU7xxYuzgBX (provision)
Dieser Abstand ist nicht erforderlich, wenn diese elektrischen Anlagenteile in frei zugänglichen Räumen offensichtlich unbeschädigt sind (z. B. Abstand zu Lichtschaltern und Steckdosen).
- bib.al.original-language: en
- bib.dp.publication-date: 2018-07-01
- ids.document: 7104561
- ids.element: section_5.2.4
- ids.language-synoptic: section_5.2.4
- ids.tracing: hash-a0457d135e54b8203615581ced8b2d69c79adcf1ff7317b42dcd813949ff98d0
- obj.clause-number: 5.2.4
- obj.element-name: paragraph
- obj.language: de
- obj.modality: permission
- obj.normativity: normative
- obj.specobject-type: provision
- use.business-process: undefined
- use.business-sector: undefined
- use.interaction: undefined
- use.location: undefined
- use.product-category: undefined
- use.product-life-cycle: undefined
- use.project-phase: undefined
- use.purpose: undefined

##### prov-7104561-b2af74b355cb46d: Zulässige Annäherungen in Niederspannungsanlagen (provision)
Tabelle 2 — Zulässige Annäherungen in Niederspannungsanlagen
| Nennspannung | Annäherung |
| --- | --- |
| bis AC 1 000 V oder DC 1 500 V | 1 m |
- bib.al.original-language: en
- bib.dp.publication-date: 2018-07-01
- ids.document: 7104561
- ids.element: table_2
- ids.language-synoptic: table_2
- ids.tracing: hash-744616b664f143c4d1e3fc18fba8916d5ad6241608444b3ba75d43f5aae9515e
- obj.clause-number: Tabelle 2
- obj.element-name: table
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### tr--570aeb71-321d-47c4-82c1-10e363247405--uQqBUjg40mAv (provision)
Bei Löscharbeiten gelten die Mindestabstände nach den Tabellen 5 bis 8.
- bib.al.original-language: en
- bib.dp.publication-date: 2018-07-01
- ids.document: 7104561
- ids.element: section_5.2.4
- ids.language-synoptic: section_5.2.4
- ids.tracing: hash-94af5241d35b2d2c9d88353e3223d6e84b027b9d4bb86f958c0c40d95229aa66
- obj.clause-number: 5.2.4
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-7104561-69867da9b1324e0

### prov-7104561-ccb5d12be8ba4a5: Besondere Maßnahmen für Hochspannungsanlagen (heading)
- bib.al.original-language: en
- bib.dp.publication-date: 2018-07-01
- ids.document: 7104561
- ids.element: section_5.3
- ids.language-synoptic: section_5.3
- ids.tracing: hash-906888b6d90966e7fed8b421718915e7383a073245355b7a6649e58a32c8453f
- obj.clause-number: 5.3
- obj.element-name: heading
- obj.language: de
- obj.specobject-type: heading
- ChapterName: 5.3 Besondere Maßnahmen für Hochspannungsanlagen

#### prov-7104561-38941ac0a3c34de: 5.3.1 (heading)
- bib.al.original-language: en
- bib.dp.publication-date: 2018-07-01
- ids.document: 7104561
- ids.element: section_5.3.1
- ids.language-synoptic: section_5.3.1
- ids.tracing: hash-6344ad735bb93e1dfae19b8328265502ceb0eb354e88367d6ee0ce2bc71deeae
- obj.element-name: heading
- obj.language: de
- obj.specobject-type: heading

##### tr--570aeb71-321d-47c4-82c1-10e363247405--yBiup0l9jBey (provision)
Hochspannungsanlagen in abgeschlossenen elektrischen Betriebsstätten, wie z. B. Schalt- und Umspannanlagen, dürfen nur in Gegenwart einer für den Betrieb dieser Anlage verantwortlichen Person und nur von unmittelbar Beteiligten betreten werden.
- bib.al.original-language: en
- bib.dp.publication-date: 2018-07-01
- ids.document: 7104561
- ids.element: section_5.3.1
- ids.language-synoptic: section_5.3.1
- ids.tracing: hash-ac69fd185bc136b27af70153c16e6cb77fad3f83dce5b981ec941dedf58e3bb7
- obj.clause-number: 5.3.1
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### tr--570aeb71-321d-47c4-82c1-10e363247405--icIKH7qv4mn9 (provision)
Zur Rettung von Menschenleben ist das Betreten auch bei Abwesenheit dieser Person möglich, wenn eine Elektrofachkraft anwesend ist, die über spezielle Kenntnisse für Hochspannungsanlagen der entsprechenden Spannungsebene verfügt.
- bib.al.original-language: en
- bib.dp.publication-date: 2018-07-01
- ids.document: 7104561
- ids.element: section_5.3.1
- ids.language-synoptic: section_5.3.1
- ids.tracing: hash-60ffccee19aa4576134428757919706ac25ded7f22dd412e022c0038f98a29a0
- obj.clause-number: 5.3.1
- obj.element-name: paragraph
- obj.language: de
- obj.modality: permission
- obj.normativity: normative
- obj.specobject-type: provision
- use.business-process: undefined
- use.business-sector: undefined
- use.interaction: undefined
- use.location: undefined
- use.product-category: undefined
- use.product-life-cycle: undefined
- use.project-phase: undefined
- use.purpose: undefined

##### tr--570aeb71-321d-47c4-82c1-10e363247405--hRYZLYdAhNvG (provision)
Für im unmittelbaren Einflussbereich eines Brandes liegende Anlagenteile ist – wegen der Gefahr von Lichtbogenkurzschlüssen durch leitfähige Beläge, Ionisation usw. – vor Annäherung der spannungsfreie Zustand herzustellen und sicherzustellen [siehe DIN VDE 0105-100 (VDE 0105-100):2015-10, 6.2] .
- bib.al.original-language: en
- bib.dp.publication-date: 2018-07-01
- ids.document: 7104561
- ids.element: section_5.3.1
- ids.language-synoptic: section_5.3.1
- ids.tracing: hash-8e2f1338dcb3e3ae6e072ec7409537555f7de93129a3a85087a852130df57118
- obj.clause-number: 5.3.1
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-b30112fb5a6543d: 5.3.2 (heading)
- bib.al.original-language: en
- bib.dp.publication-date: 2018-07-01
- ids.document: 7104561
- ids.element: section_5.3.2
- ids.language-synoptic: section_5.3.2
- ids.tracing: hash-3f08c9b0421d7de83367cb153f9e59eed967333b8b281c6c34bf0c9aabf061c3
- obj.element-name: heading
- obj.language: de
- obj.specobject-type: heading

##### tr--570aeb71-321d-47c4-82c1-10e363247405--GOSsAHxiKTiv (provision)
Schalthandlungen in Hochspannungsanlagen dürfen nur durch den Anlagenverantwortlichen veranlasst werden.
- bib.al.original-language: en
- bib.dp.publication-date: 2018-07-01
- ids.document: 7104561
- ids.element: section_5.3.2
- ids.language-synoptic: section_5.3.2
- ids.tracing: hash-3bf6acb77a07eaff63eedf81301822f1696d552e74c9ee4c480b10f7f82ca9f3
- obj.clause-number: 5.3.2
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-3ec30e09642d494: 5.3.3 (heading)
- bib.al.original-language: en
- bib.dp.publication-date: 2018-07-01
- ids.document: 7104561
- ids.element: section_5.3.3
- ids.language-synoptic: section_5.3.3
- ids.tracing: hash-ec139491833ed7c85f5f8091bd9999c5ac466caeaf824311cda9069ffccae67b
- obj.element-name: heading
- obj.language: de
- obj.specobject-type: heading

##### tr--570aeb71-321d-47c4-82c1-10e363247405--WvpyUqVBtySe (provision)
Hochspannungsanlagen, z. B. Freileitungen, dürfen unter keinen Umständen durch behelfsmäßiges Erden und Kurzschließen oder Durchtrennen spannungsfrei gemacht werden, weil diese Maßnahmen mit nicht überschaubaren Gefahren verbunden sind.
- bib.al.original-language: en
- bib.dp.publication-date: 2018-07-01
- ids.document: 7104561
- ids.element: section_5.3.3
- ids.language-synoptic: section_5.3.3
- ids.tracing: hash-a0ba651f8c51f8a825ef4517cd508f9e669cfabc9b1d047e605197b15794cd9d
- obj.clause-number: 5.3.3
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-24000de83ed8423: 5.3.4 (heading)
- bib.al.original-language: en
- bib.dp.publication-date: 2018-07-01
- ids.document: 7104561
- ids.element: section_5.3.4
- ids.language-synoptic: section_5.3.4
- ids.tracing: hash-ccaafacd18cb9a3780ff3caf705af114151b68e0c248783f79175fa8d553783a
- obj.element-name: heading
- obj.language: de
- obj.specobject-type: heading

##### tr--570aeb71-321d-47c4-82c1-10e363247405--YfE8T8AUDQcp (provision)
Bei Annäherung (z. B. beim Erkunden und Retten) an unter Spannung stehende Hochspannungsanlagen in nicht abgeschlossenen elektrischen Betriebsstätten, z. B. Freileitungen, sind die Mindestabstände nach Tabelle 3 einzuhalten.
- bib.al.original-language: en
- bib.dp.publication-date: 2018-07-01
- ids.document: 7104561
- ids.element: section_5.3.4
- ids.language-synoptic: section_5.3.4
- ids.tracing: hash-d03ac495ff1e67a3c08d6c7e359d5970fb39737445f6af1ebd9758ed35c2ff69
- obj.clause-number: 5.3.4
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-7104561-2a77f3e81b6942f

##### tr--570aeb71-321d-47c4-82c1-10e363247405--rbBICf1QZ5kz (provision)
Bei Unterschreiten dieser Mindestabstände besteht Lebensgefahr.
- bib.al.original-language: en
- bib.dp.publication-date: 2018-07-01
- ids.document: 7104561
- ids.element: section_5.3.4
- ids.language-synoptic: section_5.3.4
- ids.tracing: hash-51c497a73d2044b3fccac47e972540c40ac62b0bd8525fdb7dcaa81bc7e64086
- obj.clause-number: 5.3.4
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### prov-7104561-2a77f3e81b6942f: Zulässige Annäherungen in Hochspannungsanlagen (provision)
Tabelle 3 — Zulässige Annäherungen in Hochspannungsanlagen
| Nennspannung | Annäherung |
| --- | --- |
| bis 110 kV | 3 m |
| über 110 kV bis 220 kV | 4 m |
| über 220 kV bis 380 kV | 5 m |
- bib.al.original-language: en
- bib.dp.publication-date: 2018-07-01
- ids.document: 7104561
- ids.element: table_3
- ids.language-synoptic: table_3
- ids.tracing: hash-75550db5120ff95e886cbae6f1351ee06215a78a0c3d332f83262b4ba43f2ed9
- obj.clause-number: Tabelle 3
- obj.element-name: table
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### tr--570aeb71-321d-47c4-82c1-10e363247405--6FKjnpuKHZNP (provision)
Unter Aufsicht von Elektrofachkräften oder elektrotechnisch unterwiesenen Personen ist eine Annäherung bis auf die Werte nach DIN VDE 0105-100 (VDE 0105-100):2015-10, Tabelle 102 möglich.
- bib.al.original-language: en
- bib.dp.publication-date: 2018-07-01
- ids.document: 7104561
- ids.element: section_5.3.4
- ids.language-synoptic: section_5.3.4
- ids.tracing: hash-b3d8346bf03491160637028e4afe02e3f8924cd9cc1286b2849589c65912c000
- obj.clause-number: 5.3.4
- obj.element-name: paragraph
- obj.language: de
- obj.modality: permission
- obj.normativity: normative
- obj.specobject-type: provision
- use.business-process: undefined
- use.business-sector: undefined
- use.interaction: undefined
- use.location: undefined
- use.product-category: undefined
- use.product-life-cycle: undefined
- use.project-phase: undefined
- use.purpose: undefined

##### tr--570aeb71-321d-47c4-82c1-10e363247405--RIRGOkbUq5lB (provision)
Bei Rettungsarbeiten an Oberleitungen elektrischer Bahnen (bis 25 kV) ist eine Annäherung bis auf 1,5 m möglich [siehe DIN VDE 0105-103 (VDE 0105-103):2014-10, 6.4 .302].
- bib.al.original-language: en
- bib.dp.publication-date: 2018-07-01
- ids.document: 7104561
- ids.element: section_5.3.4
- ids.language-synoptic: section_5.3.4
- ids.tracing: hash-07bd69f54c677236926b7b309f87f4558f2cec2c049283a67aa5a8210c70a7c2
- obj.clause-number: 5.3.4
- obj.element-name: paragraph
- obj.language: de
- obj.modality: permission
- obj.normativity: normative
- obj.specobject-type: provision
- use.business-process: undefined
- use.business-sector: undefined
- use.interaction: undefined
- use.location: undefined
- use.product-category: undefined
- use.product-life-cycle: undefined
- use.project-phase: undefined
- use.purpose: undefined

##### tr--570aeb71-321d-47c4-82c1-10e363247405--DMgX29qMPkxm (provision)
Bei Löscharbeiten gelten die Mindestabstände nach den Tabellen 5 bis 8.
- bib.al.original-language: en
- bib.dp.publication-date: 2018-07-01
- ids.document: 7104561
- ids.element: section_5.3.4
- ids.language-synoptic: section_5.3.4
- ids.tracing: hash-5f33bcdfffd295a3cf954827f3151f14c64c838e2a2a79320303ef9d00e2c380
- obj.clause-number: 5.3.4
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-7104561-69867da9b1324e0

#### prov-7104561-80f799700b314a0: 5.3.5 (heading)
- bib.al.original-language: en
- bib.dp.publication-date: 2018-07-01
- ids.document: 7104561
- ids.element: section_5.3.5
- ids.language-synoptic: section_5.3.5
- ids.tracing: hash-afe32270783b9f8d71a2b86ffcb4b49a18d209dcfa458138973ed50643ab10ab
- obj.element-name: heading
- obj.language: de
- obj.specobject-type: heading

##### tr--570aeb71-321d-47c4-82c1-10e363247405--fSEX9fTS1cVp (provision)
Freileitungen und Fahrleitungen in der Nähe von Einsatzstellen können beschädigt werden und herunterfallen.
- bib.al.original-language: en
- bib.dp.publication-date: 2018-07-01
- ids.document: 7104561
- ids.element: section_5.3.5
- ids.language-synoptic: section_5.3.5
- ids.tracing: hash-3187122293dd2932131feb29a058e3d4ad7fc6ccb9d2fbd439190c957993bdbc
- obj.clause-number: 5.3.5
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### tr--570aeb71-321d-47c4-82c1-10e363247405--wO4AGyRt0cWe (provision)
Das Betreten der Umgebung von herabgefallenen, unter Spannung stehenden Leitungen ist lebensgefährlich (Schrittspannung, siehe Bild 1).
- bib.al.original-language: en
- bib.dp.publication-date: 2018-07-01
- ids.document: 7104561
- ids.element: section_5.3.5
- ids.language-synoptic: section_5.3.5
- ids.tracing: hash-b5378bc296aa3ac9aa7787f3faf1884c024c3c07cac17110f885b4296403f50f
- obj.clause-number: 5.3.5
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-7104561-9acf97ebc2404d7

##### prov-7104561-9acf97ebc2404d7 (provision)
Bild 1 — SchrittspannungU _S im Bereich einer Fehlerstelle bei der Schrittlänge l _S
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| Legende |  |
| --- | --- |
| U _S1 | Schrittspannung 1 |
| U _S2 | Schrittspannung 2 |
| l _S | Schrittlänge |
- bib.al.original-language: en
- bib.dp.publication-date: 2018-07-01
- ids.document: 7104561
- ids.element: section_5.3.5
- ids.language-synoptic: section_5.3.5
- ids.tracing: hash-6794393bd5cbb216c0e2db82e735a0c63ae0aa1a056628e7ad5c976c6434f792
- obj.clause-number: 5.3.5
- obj.element-name: figure
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### tr--570aeb71-321d-47c4-82c1-10e363247405--Ob7uDF7EAUgx (provision)
Von der am Boden liegenden Freileitung ist daher ein Abstand von mindestens 20 m, von der am Boden liegenden Fahrleitung ein Abstand von 10 m einzuhalten.
- bib.al.original-language: en
- bib.dp.publication-date: 2018-07-01
- ids.document: 7104561
- ids.element: section_5.3.5
- ids.language-synoptic: section_5.3.5
- ids.tracing: hash-edc09d7170f9f4f8b072538b9368fe1cbc85f2545d1c97c39e716d5d183ccb36
- obj.clause-number: 5.3.5
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### tr--570aeb71-321d-47c4-82c1-10e363247405--hOdSiql0vWA7 (provision)
Hat die betreffende Leitung Berührung mit Metallteilen wie Zäunen, Geländern, Schienen usw., so ist von diesen Teilen ebenfalls der entsprechende Abstand einzuhalten.
- bib.al.original-language: en
- bib.dp.publication-date: 2018-07-01
- ids.document: 7104561
- ids.element: section_5.3.5
- ids.language-synoptic: section_5.3.5
- ids.tracing: hash-4c50ee17b605409c5ea6036620b67f6cdffd3b8fc6e9308b7d7d0e05de6ff9a2
- obj.clause-number: 5.3.5
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### tr--570aeb71-321d-47c4-82c1-10e363247405--V7taZT9GLMMb (provision)
Die Gefahrenzone ist abzusperren.
- bib.al.original-language: en
- bib.dp.publication-date: 2018-07-01
- ids.document: 7104561
- ids.element: section_5.3.5
- ids.language-synoptic: section_5.3.5
- ids.tracing: hash-7922112b0455889c8e415d4622976fabb27ec107fa197b0c8452b2ffe3f2358e
- obj.clause-number: 5.3.5
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### tr--570aeb71-321d-47c4-82c1-10e363247405--GP5LCCttZA2V (provision)
Der Bereich darf erst wieder nach Beseitigung der Gefahr und Freigabe durch den Anlagenbetreiber betreten werden.
- bib.al.original-language: en
- bib.dp.publication-date: 2018-07-01
- ids.document: 7104561
- ids.element: section_5.3.5
- ids.language-synoptic: section_5.3.5
- ids.tracing: hash-ed3c54628c98c12d1b31fe7d77c915257d4929a0474dc23c074fc7894ca92304
- obj.clause-number: 5.3.5
- obj.element-name: paragraph
- obj.language: de
- obj.modality: permission
- obj.normativity: normative
- obj.specobject-type: provision
- use.business-process: undefined
- use.business-sector: undefined
- use.interaction: undefined
- use.location: undefined
- use.product-category: undefined
- use.product-life-cycle: undefined
- use.project-phase: undefined
- use.purpose: undefined

##### prov-7104561-0cb6fa6d738e484: , Note (provision)
ANMERKUNG:
Mit den vorstehenden Abständen soll sichergestellt werden, dass selbst bei ungünstigen Bedingungen keine Gefährdung für die Einsatzkräfte vorliegt. Ungünstige Bedingungen liegen z. B. bei gelöschten 110-kV-Netzen und gleichzeitig hohen spezifischen Erdwiderständen vor.
- bib.al.original-language: en
- bib.dp.publication-date: 2018-07-01
- ids.document: 7104561
- ids.element: section_5.3.5
- ids.language-synoptic: section_5.3.5
- ids.tracing: hash-9fb9b32c53d9b11479734a3a717e88b2c122dce85820d51afea14557b53272de
- obj.clause-number: 5.3.5
- obj.element-name: note
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

##### tr--570aeb71-321d-47c4-82c1-10e363247405--frUOblLra5WM (provision)
Jedoch kann eine Elektrofachkraft des betreffenden Anlagenbetreibers des Elektrizitätsversorgungsnetzes, die beurteilen kann, um welche Netzspannungsebene und Art der Sternpunkterdung es sich handelt, vor Ort den Einsatzkräften empfehlen, auf welchen Wert der Schutzabstand gegebenenfalls unter 20 m verringert werden kann.
- bib.al.original-language: en
- bib.dp.publication-date: 2018-07-01
- ids.document: 7104561
- ids.element: section_5.3.5
- ids.language-synoptic: section_5.3.5
- ids.tracing: hash-1b566fcc4d70cad12e741d567aea31bda2fd7c901c7ae287b573d8deccf121b0
- obj.clause-number: 5.3.5
- obj.element-name: paragraph
- obj.language: de
- obj.modality: permission
- obj.normativity: normative
- obj.specobject-type: provision
- obj.transformation-issues: Possibly wrong modal verb
- use.business-process: undefined
- use.business-sector: undefined
- use.interaction: undefined
- use.location: undefined
- use.product-category: undefined
- use.product-life-cycle: undefined
- use.project-phase: undefined
- use.purpose: undefined

##### tr--570aeb71-321d-47c4-82c1-10e363247405--jcKg2e62Tcni (provision)
Dabei kann in Betracht gezogen werden, dass z. B.:
- in Niederspannungsnetzen keine gefahrbringenden Schrittspannungen vorkommen;
- im Hochspannungsbereich bis 30 kV (Mittelspannungsbereich) der Schutzabstand auf bis zu 10 m reduziert werden kann;
- bei den Spannungsebenen 220 kV und 380 kV die Sternpunkte grundsätzlich niederohmig geerdet sind und ein Erdschluss daher in kurzer Zeit abgeschaltet wird; das Gleiche gilt auch für niederohmig geerdete 110-kV-Netze;
- in gelöschten 110-kV-Netzen und gleichzeitig hohen spezifischen Erdwiderständen eine Reduzierung des Schutzabstandes unter 20 m nicht empfohlen wird.
- bib.al.original-language: en
- bib.dp.publication-date: 2018-07-01
- ids.document: 7104561
- ids.element: section_5.3.5
- ids.language-synoptic: section_5.3.5
- ids.tracing: hash-7cd11ce12fdd2431db22e1ec2fbc9210d31fa1c2eff8298387f975b41b60b96d
- obj.clause-number: 5.3.5
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### tr--570aeb71-321d-47c4-82c1-10e363247405--VRl9rkTZXf1W (provision)
Den Angaben für den Schutzabstand liegen die Annahmen eines spezifischen Erdwiderstandes von 1 000 Ωm, eines Erdschlussreststromes von 132 A sowie einer maximalen Schrittspannung von 75 V zugrunde.
- bib.al.original-language: en
- bib.dp.publication-date: 2018-07-01
- ids.document: 7104561
- ids.element: section_5.3.5
- ids.language-synoptic: section_5.3.5
- ids.tracing: hash-0b6a9c4f7e0881ea5e04d89c68ca92a1030cb9dcdfa56c7bbdb970ae2ad51f5e
- obj.clause-number: 5.3.5
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-61ca9ad7e12d4b1: Besondere Maßnahmen für Anlagen mit starken Magnetfeldern – supraleitende Magnete (heading)
- bib.al.original-language: en
- bib.dp.publication-date: 2018-07-01
- ids.document: 7104561
- ids.element: section_5.4
- ids.language-synoptic: section_5.4
- ids.tracing: hash-117b3159ec5188a4c75702cc1f5323e4b91815fbfb2328ace23994a5e01977d0
- obj.clause-number: 5.4
- obj.element-name: heading
- obj.language: de
- obj.specobject-type: heading
- ChapterName: 5.4 Besondere Maßnahmen für Anlagen mit starken Magnetfeldern – supraleitende Magnete

#### prov-7104561-305979c57a594d0: Magnetische Supraleiter und deren Anwendungen (heading)
- bib.al.original-language: en
- bib.dp.publication-date: 2018-07-01
- ids.document: 7104561
- ids.element: section_5.4.1
- ids.language-synoptic: section_5.4.1
- ids.tracing: hash-f565c5020c1f1fa066fc46c94d26bf99abaae4b8f77bec927311fa4420fd0666
- obj.clause-number: 5.4.1
- obj.element-name: heading
- obj.language: de
- obj.specobject-type: heading
- ChapterName: 5.4.1 Magnetische Supraleiter und deren Anwendungen

##### prov-7104561-a74cabad74e04d8: Allgemeines (heading)
- bib.al.original-language: en
- bib.dp.publication-date: 2018-07-01
- ids.document: 7104561
- ids.element: section_5.4.1.1
- ids.language-synoptic: section_5.4.1.1
- ids.tracing: hash-106b431f020982aeee0c1216a9588efab63f89d2c11d54fcb83b3d4114daa048
- obj.clause-number: 5.4.1.1
- obj.element-name: heading
- obj.language: de
- obj.specobject-type: heading
- ChapterName: 5.4.1.1 Allgemeines

###### tr--570aeb71-321d-47c4-82c1-10e363247405--mOmb8lQzECGS: Allgemeines (provision)
Supraleitende Magnete werden
- in Forschungseinrichtungen (bis zu 20 Tesla) und
- vor allem im medizinischen Bereich der Kernspintomographen bzw. Magnetresonanztomographen (MRT) mit 0,5 Tesla bis 7 Tesla
verwendet.
- bib.al.original-language: en
- bib.dp.publication-date: 2018-07-01
- ids.document: 7104561
- ids.element: section_5.4.1.1
- ids.language-synoptic: section_5.4.1.1
- ids.tracing: hash-e6a53857c4ae8fbf5ac7505013eda4a014eb75cd38ff50a8dea8f20bb6a470e5
- obj.clause-number: 5.4.1.1
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

###### prov-7104561-53237e958b42452: Allgemeines, Note (provision)
ANMERKUNG 1:
Supraleitende Magnete werden auch als elektrische Energiespeicher und als Kurzschlussstrombegrenzer in Hochspannungsnetzen eingesetzt (z. B. Hochspannungsgleichstromübertragung – HGÜ).
- bib.al.original-language: en
- bib.dp.publication-date: 2018-07-01
- ids.document: 7104561
- ids.element: section_5.4.1.1
- ids.language-synoptic: section_5.4.1.1
- ids.tracing: hash-6437358b71fa96629428d572690ddc8bf95964040307e716c0983d2627d6f4f6
- obj.clause-number: 5.4.1.1
- obj.element-name: note
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

###### prov-7104561-47894a9281bf4b1: Allgemeines, Note (provision)
ANMERKUNG 2:
Ein Tesla entspricht der 10 000-fachen Stärke des Erdmagnetfeldes.
- bib.al.original-language: en
- bib.dp.publication-date: 2018-07-01
- ids.document: 7104561
- ids.element: section_5.4.1.1
- ids.language-synoptic: section_5.4.1.1
- ids.tracing: hash-0a624e1c63bb95603911f826fd6ab45664cb5a68defd4acc7fb94b30c6e70573
- obj.clause-number: 5.4.1.1
- obj.element-name: note
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

##### prov-7104561-1743c0a689a2454: Gefährdungen (heading)
- bib.al.original-language: en
- bib.dp.publication-date: 2018-07-01
- ids.document: 7104561
- ids.element: section_5.4.1.2
- ids.language-synoptic: section_5.4.1.2
- ids.tracing: hash-51abba29f3ece2511678888fb415dab6a2b61e2a669d125a2572206d9c4f2c54
- obj.clause-number: 5.4.1.2
- obj.element-name: heading
- obj.language: de
- obj.specobject-type: heading
- ChapterName: 5.4.1.2 Gefährdungen

###### prov-7104561-4e080ba54e1f448: Gefährdungen (provision)
Das Magnetfeld bei Supraleitern ist dauerhaft auch bei abgeschalteter Stromversorgung vorhanden.
- bib.al.original-language: en
- bib.dp.publication-date: 2018-07-01
- ids.document: 7104561
- ids.element: section_5.4.1.2
- ids.language-synoptic: section_5.4.1.2
- ids.tracing: hash-de2e09573aba620e00b02813a93aa26b867cbb0af25fb82dd113591f54e944ff
- obj.clause-number: 5.4.1.2
- obj.element-name: paragraph
- obj.language: de
- obj.modality: undefined
- obj.normativity: normative
- obj.specobject-type: provision
- obj.transformation-issues: not annotated
- use.business-process: undefined
- use.business-sector: undefined
- use.interaction: undefined
- use.location: undefined
- use.product-category: undefined
- use.product-life-cycle: undefined
- use.project-phase: undefined
- use.purpose: undefined

###### tr--570aeb71-321d-47c4-82c1-10e363247405--xTuiMhttG5GK: Gefährdungen (provision)
Sämtliche ferromagnetischen Teile können in das Magnetfeld gezogen werden.
- bib.al.original-language: en
- bib.dp.publication-date: 2018-07-01
- ids.document: 7104561
- ids.element: section_5.4.1.2
- ids.language-synoptic: section_5.4.1.2
- ids.tracing: hash-c2c2daceba33450d44809394fd1f2a9a37a17785c7e24f9bcc884416bddf4cc7
- obj.clause-number: 5.4.1.2
- obj.element-name: paragraph
- obj.language: de
- obj.modality: permission
- obj.normativity: normative
- obj.specobject-type: provision
- obj.transformation-issues: Possibly wrong modal verb
- use.business-process: undefined
- use.business-sector: undefined
- use.interaction: undefined
- use.location: undefined
- use.product-category: undefined
- use.product-life-cycle: undefined
- use.project-phase: undefined
- use.purpose: undefined

###### tr--570aeb71-321d-47c4-82c1-10e363247405--1VqCGfnGgyYV: Gefährdungen (provision)
Eine besondere Gefährdung besteht für Einsatzkräfte mit ferromagnetischen Atemschutzflaschen.
- bib.al.original-language: en
- bib.dp.publication-date: 2018-07-01
- ids.document: 7104561
- ids.element: section_5.4.1.2
- ids.language-synoptic: section_5.4.1.2
- ids.tracing: hash-5004cd826f0ae79f857c44f4363c756bd49ffc0af57848856d0e5160cbde2728
- obj.clause-number: 5.4.1.2
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

###### tr--570aeb71-321d-47c4-82c1-10e363247405--5AdjrK2L7NVK: Gefährdungen (provision)
Der Atemschutzgeräteträger kann unvermittelt in oder an den supraleitenden Magneten gezogen werden.
- bib.al.original-language: en
- bib.dp.publication-date: 2018-07-01
- ids.document: 7104561
- ids.element: section_5.4.1.2
- ids.language-synoptic: section_5.4.1.2
- ids.tracing: hash-052d39723826949cfc408ef3e6b536a78aa44bce87e5abb0b780096eed529b78
- obj.clause-number: 5.4.1.2
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

###### tr--570aeb71-321d-47c4-82c1-10e363247405--Rp2ooJYPJBMa: Gefährdungen (provision)
Auch können Ausrüstungsgegenstände, Werkzeuge, Feuerlöscher, Krankenbetten oder Ähnliches in oder an supraleitende Magnete gezogen werden.
- bib.al.original-language: en
- bib.dp.publication-date: 2018-07-01
- ids.document: 7104561
- ids.element: section_5.4.1.2
- ids.language-synoptic: section_5.4.1.2
- ids.tracing: hash-3df76fd33cd89b7495390b6490e4da75c443a7a2cb0cc0fe40c0bc806d982156
- obj.clause-number: 5.4.1.2
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### prov-7104561-50442fb54cf34e3: Maßnahmen (heading)
- bib.al.original-language: en
- bib.dp.publication-date: 2018-07-01
- ids.document: 7104561
- ids.element: section_5.4.1.3
- ids.language-synoptic: section_5.4.1.3
- ids.tracing: hash-fac5e4272b8c2fe6ef57b93c155cb7d52ee11bb1dcb7936a6308d717383dc666
- obj.clause-number: 5.4.1.3
- obj.element-name: heading
- obj.language: de
- obj.specobject-type: heading
- ChapterName: 5.4.1.3 Maßnahmen

###### tr--570aeb71-321d-47c4-82c1-10e363247405--6aXMKZ02hpB4: Maßnahmen (provision)
Nur die benötigten Einsatzkräfte dürfen den unmittelbaren Gefahrenbereich (in der Regel den betroffenen Raum) betreten.
- bib.al.original-language: en
- bib.dp.publication-date: 2018-07-01
- ids.document: 7104561
- ids.element: section_5.4.1.3
- ids.language-synoptic: section_5.4.1.3
- ids.tracing: hash-83191772120678ec423a3c9b7d1ff87b058bc9bbd24e9ea6b7a2be13521ba963
- obj.clause-number: 5.4.1.3
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

###### tr--570aeb71-321d-47c4-82c1-10e363247405--3jQ0HtLF3glJ: Maßnahmen (provision)
Dabei sollten diese Einsatzkräfte den größtmöglichen Abstand halten.
- bib.al.original-language: en
- bib.dp.publication-date: 2018-07-01
- ids.document: 7104561
- ids.element: section_5.4.1.3
- ids.language-synoptic: section_5.4.1.3
- ids.tracing: hash-0075d25135617ec49117273972ca59a05b75f09c10a9389f77467843a8a1a6bb
- obj.clause-number: 5.4.1.3
- obj.element-name: paragraph
- obj.language: de
- obj.modality: recommendation
- obj.normativity: normative
- obj.specobject-type: provision
- use.business-process: undefined
- use.business-sector: undefined
- use.interaction: undefined
- use.location: undefined
- use.product-category: undefined
- use.product-life-cycle: undefined
- use.project-phase: undefined
- use.purpose: undefined

###### tr--570aeb71-321d-47c4-82c1-10e363247405--Il7LazE780q6: Maßnahmen (provision)
Das Betreten von Räumen mit starken Magnetfeldern ist nur mit nicht ferromagnetischen Ausrüstungsgegenständen, z. B. Komposit-Atemschutzflaschen, zulässig.
- bib.al.original-language: en
- bib.dp.publication-date: 2018-07-01
- ids.document: 7104561
- ids.element: section_5.4.1.3
- ids.language-synoptic: section_5.4.1.3
- ids.tracing: hash-2067c9183b41db4e81d884e461e0ef5174497fc52c55c96b15c824a75fc5dbdb
- obj.clause-number: 5.4.1.3
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

###### tr--570aeb71-321d-47c4-82c1-10e363247405--oiytuA4TUe8j: Maßnahmen (provision)
Zum Löschen von Entstehungsbränden dürfen nur nicht ferromagnetische Feuerlöscher verwendet werden (Handelsbegriff: „antimagnetisch“).
- bib.al.original-language: en
- bib.dp.publication-date: 2018-07-01
- ids.document: 7104561
- ids.element: section_5.4.1.3
- ids.language-synoptic: section_5.4.1.3
- ids.tracing: hash-748e377cc51d4a95da66621e9b2c5d25bb4aa160e6bd524561429b8b13c5cb11
- obj.clause-number: 5.4.1.3
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

###### tr--570aeb71-321d-47c4-82c1-10e363247405--1UAZ5eDTRCPF: Maßnahmen (provision)
Eine schnelle Abschaltung des Magnetfeldes ist nur in Form einer Notabschaltung über ein Ablassen des Kühlmittels (in der Regel flüssiges Helium bei 4 K) möglich.
- bib.al.original-language: en
- bib.dp.publication-date: 2018-07-01
- ids.document: 7104561
- ids.element: section_5.4.1.3
- ids.language-synoptic: section_5.4.1.3
- ids.tracing: hash-d40cd09ffcce7f092d54415706a32b821099bff58857c1dfacf2baef90a0ae77
- obj.clause-number: 5.4.1.3
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

###### tr--570aeb71-321d-47c4-82c1-10e363247405--lZYGOvxqVkgr: Maßnahmen (provision)
Eine Notabschaltung des Magnetfeldes kann eine Gefährdung durch ausströmendes tiefkaltes Gas verursachen.
- bib.al.original-language: en
- bib.dp.publication-date: 2018-07-01
- ids.document: 7104561
- ids.element: section_5.4.1.3
- ids.language-synoptic: section_5.4.1.3
- ids.tracing: hash-e8f0f137d5434652d3a8582591b045ae3fde01f13408c0d2f0ef8d1cd6605294
- obj.clause-number: 5.4.1.3
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

###### tr--570aeb71-321d-47c4-82c1-10e363247405--P4y9BVkffEo6: Maßnahmen (provision)
Die Notabschaltung der elektrischen Komponenten erfolgt über einen separaten Not-Aus-Schalter und hat keinen Einfluss auf das Magnetfeld.
- bib.al.original-language: en
- bib.dp.publication-date: 2018-07-01
- ids.document: 7104561
- ids.element: section_5.4.1.3
- ids.language-synoptic: section_5.4.1.3
- ids.tracing: hash-2a5e12f175d812eb31a13298c4b73a5408747e749c1ff7d4dd5feb9c91fe5a1e
- obj.clause-number: 5.4.1.3
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

###### tr--570aeb71-321d-47c4-82c1-10e363247405--Rt5OpMHoe1FS: Maßnahmen (provision)
Abschaltungen sind, außer bei Lebensgefahr, zuvor mit dem Anlagenbetreiber abzusprechen.
- bib.al.original-language: en
- bib.dp.publication-date: 2018-07-01
- ids.document: 7104561
- ids.element: section_5.4.1.3
- ids.language-synoptic: section_5.4.1.3
- ids.tracing: hash-d38ba7e5ec6f671b87a52c5564cbbad505f62a7a1c22108e6630391320447e1a
- obj.clause-number: 5.4.1.3
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

###### prov-7104561-5b0209dbab934f1: Maßnahmen, Note (provision)
ANMERKUNG:
Eine Notabschaltung verursacht sehr hohe Kosten und kann zu einer Beschädigung oder Zerstörung des Magneten führen.
- bib.al.original-language: en
- bib.dp.publication-date: 2018-07-01
- ids.document: 7104561
- ids.element: section_5.4.1.3
- ids.language-synoptic: section_5.4.1.3
- ids.tracing: hash-b8059cec67cd32663b6ec960d883e7bb545db3cb2e3e33d96068add56eefe88e
- obj.clause-number: 5.4.1.3
- obj.element-name: note
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

## prov-7104561-c7f47eb35faf47e: Eignung von Löschmitteln (heading)
- bib.al.original-language: en
- bib.dp.publication-date: 2018-07-01
- ids.document: 7104561
- ids.element: section_6
- ids.language-synoptic: section_6
- ids.tracing: hash-2deb56c65012392b2ddc957d29bfa6492446167123032ff6f7fdce873ecb4c0e
- obj.clause-number: 6
- obj.element-name: heading
- obj.language: de
- obj.specobject-type: heading
- ChapterName: 6 Eignung von Löschmitteln

### prov-7104561-7405a9173551438: Auswahl der Löschmittel (heading)
- bib.al.original-language: en
- bib.dp.publication-date: 2018-07-01
- ids.document: 7104561
- ids.element: section_6.1
- ids.language-synoptic: section_6.1
- ids.tracing: hash-210980fbb08bcd3a353667a3321d76b8143c79f5b6bfc21342989848fb31a3b7
- obj.clause-number: 6.1
- obj.element-name: heading
- obj.language: de
- obj.specobject-type: heading
- ChapterName: 6.1 Auswahl der Löschmittel

#### tr--570aeb71-321d-47c4-82c1-10e363247405--GR3pFXcxOUg7: Auswahl der Löschmittel (provision)
Als Löschmittel können z. B. eingesetzt werden:
- Wasser;
- Schaum;
- Pulver;
- Kohlenstoffdioxid.
- bib.al.original-language: en
- bib.dp.publication-date: 2018-07-01
- ids.document: 7104561
- ids.element: section_6.1
- ids.language-synoptic: section_6.1
- ids.tracing: hash-da6d229225bb11ed0921859554969da49fdb531809f9e21f0f8b8a03c411f0b1
- obj.clause-number: 6.1
- obj.element-name: paragraph
- obj.language: de
- obj.modality: permission
- obj.normativity: normative
- obj.specobject-type: provision
- obj.transformation-issues: Possibly wrong modal verb
- use.business-process: undefined
- use.business-sector: undefined
- use.interaction: undefined
- use.location: undefined
- use.product-category: undefined
- use.product-life-cycle: undefined
- use.project-phase: undefined
- use.purpose: undefined

#### tr--570aeb71-321d-47c4-82c1-10e363247405--xGSfthPLJegW: Auswahl der Löschmittel (provision)
Diese Löschmittel sind unter Beachtung ihrer Eignung und eventueller Einsatzbeschränkungen auszuwählen.
- bib.al.original-language: en
- bib.dp.publication-date: 2018-07-01
- ids.document: 7104561
- ids.element: section_6.1
- ids.language-synoptic: section_6.1
- ids.tracing: hash-167f10fb572e90f9869e1133aeb7495a65a6afab70976b513899a90334d5982b
- obj.clause-number: 6.1
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-317d9964fad7445: Anwendung von Löschmitteln (heading)
- bib.al.original-language: en
- bib.dp.publication-date: 2018-07-01
- ids.document: 7104561
- ids.element: section_6.2
- ids.language-synoptic: section_6.2
- ids.tracing: hash-56bbcaabecaf93a1e4ebf44deeec6e26786ef18a48d0609a761dd2bcccce0f54
- obj.clause-number: 6.2
- obj.element-name: heading
- obj.language: de
- obj.specobject-type: heading
- ChapterName: 6.2 Anwendung von Löschmitteln

#### prov-7104561-bf42099ff40b487: Allgemeines (heading)
- bib.al.original-language: en
- bib.dp.publication-date: 2018-07-01
- ids.document: 7104561
- ids.element: section_6.2.1
- ids.language-synoptic: section_6.2.1
- ids.tracing: hash-7d19ef1e0ab6eda709358782637925919f3869ace9b03de04817045271419891
- obj.clause-number: 6.2.1
- obj.element-name: heading
- obj.language: de
- obj.specobject-type: heading
- ChapterName: 6.2.1 Allgemeines

##### tr--570aeb71-321d-47c4-82c1-10e363247405--H8vF35Er4Bmg: Allgemeines (provision)
Die in den Tabellen 5 bis 8 genannten Mindestabstände zwischen Löschmittelaustrittsöffnung und unter Spannung stehenden Teilen der elektrischen Anlagen sind erforderlich, um Stromeinwirkungen auf das den Löscheinsatz durchführende Personal zu verhindern.
- bib.al.original-language: en
- bib.dp.publication-date: 2018-07-01
- ids.document: 7104561
- ids.element: section_6.2.1
- ids.language-synoptic: section_6.2.1
- ids.tracing: hash-bde40f3be5ac3111c0354de0219f454c04a49c20866a9f82611544f36ae15185
- obj.clause-number: 6.2.1
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-7104561-69867da9b1324e0

##### tr--570aeb71-321d-47c4-82c1-10e363247405--zQr46hbWxiIU: Allgemeines (provision)
Dabei ist nicht nur die Gefährdung durch den elektrischen Strom, sondern auch die Gefährdung durch reflexartige Handlungen zu verhindern.
- bib.al.original-language: en
- bib.dp.publication-date: 2018-07-01
- ids.document: 7104561
- ids.element: section_6.2.1
- ids.language-synoptic: section_6.2.1
- ids.tracing: hash-586bf695bc73640fc39639222cb2f36f596006e76413f08e2f1a881d0fd7f422
- obj.clause-number: 6.2.1
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### tr--570aeb71-321d-47c4-82c1-10e363247405--QqdgyC51Q87p: Allgemeines (provision)
Das ist gegeben, wenn der Stromfluss über den menschlichen Körper nicht wahrnehmbar ist.
- bib.al.original-language: en
- bib.dp.publication-date: 2018-07-01
- ids.document: 7104561
- ids.element: section_6.2.1
- ids.language-synoptic: section_6.2.1
- ids.tracing: hash-c22b8224ec2e1447f7400cbae3e5f516fc77cc17e4f2ff7ce10745e7770e8b4f
- obj.clause-number: 6.2.1
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### tr--570aeb71-321d-47c4-82c1-10e363247405--JVaiKmJsWrol: Allgemeines (provision)
Bei Bränden in abgeschlossenen Betriebsstätten dürfen unter Spannung stehende Anlagenteile nur im Einvernehmen mit dem Anlagenverantwortlichen mit Wasser angespritzt werden.
- bib.al.original-language: en
- bib.dp.publication-date: 2018-07-01
- ids.document: 7104561
- ids.element: section_6.2.1
- ids.language-synoptic: section_6.2.1
- ids.tracing: hash-d19e42648e1e1daaf664702c172c96f9336e45aa6259a6acba0c8a68efe20b38
- obj.clause-number: 6.2.1
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### tr--570aeb71-321d-47c4-82c1-10e363247405--opouvOE4bHY8: Allgemeines (provision)
Das Einvernehmen kann auch durch vorherige Absprache hergestellt werden.
- bib.al.original-language: en
- bib.dp.publication-date: 2018-07-01
- ids.document: 7104561
- ids.element: section_6.2.1
- ids.language-synoptic: section_6.2.1
- ids.tracing: hash-ee75c944aab61efcbedcaf68277d6930513e487a1d003cbc613475492dc51133
- obj.clause-number: 6.2.1
- obj.element-name: paragraph
- obj.language: de
- obj.modality: permission
- obj.normativity: normative
- obj.specobject-type: provision
- obj.transformation-issues: Possibly wrong modal verb
- use.business-process: undefined
- use.business-sector: undefined
- use.interaction: undefined
- use.location: undefined
- use.product-category: undefined
- use.product-life-cycle: undefined
- use.project-phase: undefined
- use.purpose: undefined

##### tr--570aeb71-321d-47c4-82c1-10e363247405--JQFgungt0Wet: Allgemeines (provision)
Sind den Einsatzkräften die anstehenden Spannungen und die örtlichen Verhältnisse zunächst unbekannt, so dürfen beim Einsatz von Strahlrohren CM nach DIN 14365-1 zwischen Strahlrohr und unter Spannung stehenden Anlagenteilen die Richtwerte nach Tabelle 4 nicht unterschritten werden.
- bib.al.original-language: en
- bib.dp.publication-date: 2018-07-01
- ids.document: 7104561
- ids.element: section_6.2.1
- ids.language-synoptic: section_6.2.1
- ids.tracing: hash-9d87c338abff27a3dc1365ec6f7c3d58970a4765c677f59c084450ec56f7b8bf
- obj.clause-number: 6.2.1
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-7104561-f97005fc5e22436

##### tr--570aeb71-321d-47c4-82c1-10e363247405--MjMxejUTnzpS: Allgemeines (provision)
Im Zweifelsfall ist immer der höchste Abstand einzuhalten.
- bib.al.original-language: en
- bib.dp.publication-date: 2018-07-01
- ids.document: 7104561
- ids.element: section_6.2.1
- ids.language-synoptic: section_6.2.1
- ids.tracing: hash-fb0c43000a50bfe356f3441817ac3f13102443c3ef660dc5aac5d877f32f3e3a
- obj.clause-number: 6.2.1
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### prov-7104561-f97005fc5e22436: Richtwerte (provision)
Tabelle 4 — Richtwerte
| Strahlrohr DIN 14365-CM | Niederspannung (N) ≤ AC 1 kV oder ≤ DC 1,5 kV | Hochspannung (H) > AC 1 kV oder > DC 1,5 kV |
| --- | --- | --- |
| Sprühstrahl | 1 m | 5 m |
| Vollstrahl | 5 m | 10 m |
| Kurzzeichen | N-1-5 | H-5-10 |
- bib.al.original-language: en
- bib.dp.publication-date: 2018-07-01
- ids.document: 7104561
- ids.element: table_4
- ids.language-synoptic: table_4
- ids.tracing: hash-73032ae86ed5ff012fd7b1d9cb1727d7262c5440265c65bf2adac931ca3c832d
- obj.clause-number: Tabelle 4
- obj.element-name: table
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### tr--570aeb71-321d-47c4-82c1-10e363247405--mlEOZjLB6EZ1: Allgemeines (provision)
In Niederspannungsanlagen gelten diese Richtwerte auch für Feuerlöscher nach DIN EN 3 (alle Teile) und in allen Anlagen auch für größere Wasserlöschgeräte, wenn deren Strahlrohre im Sinne der elektrischen Sicherheit DIN 14365-2:1986-09 entsprechen.
- bib.al.original-language: en
- bib.dp.publication-date: 2018-07-01
- ids.document: 7104561
- ids.element: section_6.2.1
- ids.language-synoptic: section_6.2.1
- ids.tracing: hash-e2acc4f4aaa0d67df4918e21c0ad9b3f7555066bdeb3baf0e40c6fbcb772bd2c
- obj.clause-number: 6.2.1
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### tr--570aeb71-321d-47c4-82c1-10e363247405--RJnYaBlYbRww: Allgemeines (provision)
Die Verwendungs- bzw. Warnhinweise auf den Löschgeräten sind zu beachten.
- bib.al.original-language: en
- bib.dp.publication-date: 2018-07-01
- ids.document: 7104561
- ids.element: section_6.2.1
- ids.language-synoptic: section_6.2.1
- ids.tracing: hash-83db90e692266ff4c3fbf5ed1dd964427f4589a5b90e4dee6eae53893d38920b
- obj.clause-number: 6.2.1
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-e8461a8b6002471: Wasser (heading)
- bib.al.original-language: en
- bib.dp.publication-date: 2018-07-01
- ids.document: 7104561
- ids.element: section_6.2.2
- ids.language-synoptic: section_6.2.2
- ids.tracing: hash-6c161113ce755cfb119ecec97779e53530f81ef63e783c7fc39e0050bbd02bdb
- obj.clause-number: 6.2.2
- obj.element-name: heading
- obj.language: de
- obj.specobject-type: heading
- ChapterName: 6.2.2 Wasser

##### tr--570aeb71-321d-47c4-82c1-10e363247405--VYjLlwv3M5x3: Wasser (provision)
Für den Einsatz von Wasser gilt Tabelle 5.
- bib.al.original-language: en
- bib.dp.publication-date: 2018-07-01
- ids.document: 7104561
- ids.element: section_6.2.2
- ids.language-synoptic: section_6.2.2
- ids.tracing: hash-16f9da902c1f4360421a89438a7d0e6875eca0544bbaad8f571d71571d59e83c
- obj.clause-number: 6.2.2
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-7104561-69867da9b1324e0

##### prov-7104561-69867da9b1324e0: Löschmittel Wassera (provision)
Tabelle 5 — Löschmittel Wasser^a
| Lfd. Nr. | Geräte/Anwendungsform | Wirksame Wurfweite (Mittelwert) m | Eignung für Brandklasse nach DIN EN 2 | Mindestabstände (m) zwischen Löschmittelaustrittsöffnung und unter Spannung stehenden Anlagenteilen |  |  |  |  |
| --- | --- | --- | --- | --- | --- | --- | --- | --- |
| Lfd. Nr. | Geräte/Anwendungsform | Wirksame Wurfweite (Mittelwert) m | Eignung für Brandklasse nach DIN EN 2 | Niederspannung bis | Hochspannung bis AC |  |  |  |
| Lfd. Nr. | Geräte/Anwendungsform | Wirksame Wurfweite (Mittelwert) m | Eignung für Brandklasse nach DIN EN 2 | AC 1 000 V oder DC 1 500 V | 30 kV | 110 kV | 220 kV | 380 kV |
|  | Strahlrohre CM nach DIN 14365-1:1991-02 |  |  |  |  |  |  |  |
| 1a | Sprühstrahl | 5 (bei 5 bar Fließdruck) | A B nur eingeschränkt | 1 | 3^b | 3 | 4 | 5 |
| 1b | Vollstrahl | 10 (bei 5 bar Fließdruck) | A | 5 | 5 | 6 | 7 | 8 |
|  | Strahlrohre nach DIN EN 15182-2 (≤ 235 l/min; C-Kupplung) |  |  |  | ^Eine Gefährdungsbeurteilung ist durchzuführen, ob eine elektrische Prüfung erforderlich ist ^c |  |  |  |
| 2a | Strahlrohre nach Sprühstrahl | 3 bis 5 | A B nur eingeschränkt | 1 | ^Eine Gefährdungsbeurteilung ist durchzuführen, ob eine elektrische Prüfung erforderlich ist ^c |  |  |  |
| 2b | Vollstrahl | > 10 | A | 5 | ^Eine Gefährdungsbeurteilung ist durchzuführen, ob eine elektrische Prüfung erforderlich ist ^c |  |  |  |
| 3 | Tragbare oder fahrbare Feuerlöscher, die die Anforderung nach DIN EN 3-7:2007-10, Abschnitt 9 erfüllen | 2 bis 6 | A bzw. A + B | 1 | ^d |  |  |  |
| 4 | Tragbare oder fahrbare Feuerlöscher, die die Anforderung nach DIN EN 3-7:2007-10, Abschnitt 9 nicht erfüllen | 2 bis 6 | A bzw. A + B | Einsatz nur in spannungsfreien Anlagenteilen | Einsatz nur in spannungsfreien Anlagenteilen |  |  |  |
| - a a Bei tragbaren und fahrbaren Feuerlöschern: Wasser auch mit Zusätzen. - b b Bei Aufsicht durch elektrotechnisch unterwiesene Personen oder Elektrofachkräfte ist ein Mindestabstand von 2 m zulässig. - c c Da DIN EN 15182-1 bis DIN EN 15182-4 keine Angaben zur elektrischen Prüfung enthalten, hat der Unternehmer besondere Sorgfalt nach Betriebssicherheitsverordnung §3 (1) bzw. UVV Feuerwehr, DGUV Vorschrift 49, §29 (2) walten zu lassen. - d d Feuerlöscher nach DIN EN 3 (alle Teile) können auch für Hochspannungsanlagen typgeprüft sein. Die Verwendungshinweise auf diesen Löschgeräten sind zu beachten. |  |  |  |  |  |  |  |  |
| Gefahrenhinweise/Einsatzbeschränkungen Brände im Bereich elektrischer Anlagen sollten möglichst mit Sprühstrahl bekämpft werden. Wird bei Strahlrohren CM nach DIN 14365-1 ein Fließdruck von 5 bar überschritten, sind die angegebenen Mindestabstände bei Einsatz in Hochspannungsanlagen um zusätzlich 2 m zu vergrößern. Ist im Sonderfall, der zwischen Anlagenbetreiber und Feuerwehr abzusprechen ist, die Verwendung von Strahlrohren BM nach DIN 14365-1:1991-02 nicht zu vermeiden, erhöhen sich die Mindestabstände: – bei Verwendung mit Mundstück um 5 m; – bei Verwendung ohne Mundstück um 10 m. Die angegebenen bzw. errechneten Mindestabstände gelten auch für andere Strahlrohre, für die mindestens eine gleichhohe elektrische Sicherheit wie nach DIN 14365-2:1986-09 nachgewiesen wurde. Zur Erreichung des Schutzziels nach 6.2.1 kann der Nachweis über erforderliche Mindestabstände auch mit anderen geeigneten Prüfungen erbracht werden. Bei Wasser mit Bestandteilen, welche die Leitfähigkeit erhöhen, wie z. B. Seewasser und dergleichen, ergeben sich keine Veränderungen der Mindestabstände, jedoch ist die Bildung von leitfähigen Überzügen auf Isolatoren möglich. Wasser mit Bestandteilen, welche die Strahleigenschaft verändern, z. B. Netzmittel, darf im Bereich unter Spannung stehender elektrischer Anlagen nur eingesetzt werden, wenn die einzuhaltenden Mindestabstände in Anlehnung an DIN 14365-2:1986-09 als vorbereitende Maßnahme (siehe Abschnitt 4) für diese Anlagen ermittelt worden sind. Sonstige Geräte, wie z. B. Wasserwerfer, Sonderlöscher, dürfen im Bereich unter Spannung stehender elektrischer Anlagen nur eingesetzt werden, wenn die einzuhaltenden Mindestabstände in Anlehnung an DIN 14365-2:1986-09 als vorbereitende Maßnahme (siehe Abschnitt 4) für diese Anlagen ermittelt worden sind. |  |  |  |  |  |  |  |  |
- bib.al.original-language: en
- bib.dp.publication-date: 2018-07-01
- ids.document: 7104561
- ids.element: table_5
- ids.language-synoptic: table_5
- ids.tracing: hash-2eae3746838f367c2af20eba812196fc5414af73b4189456d246398530d9b521
- obj.clause-number: Tabelle 5
- obj.element-name: table
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-7104561-bf42099ff40b487
- cross-reference -> prov-7104561-5c875132a1f5470

##### prov-7104561-e34664ff28d3424: Wasser, Note (provision)
ANMERKUNG:
Siehe Anhang B „Erläuterungen“.
- bib.al.original-language: en
- bib.dp.publication-date: 2018-07-01
- ids.document: 7104561
- ids.element: section_6.2.2
- ids.language-synoptic: section_6.2.2
- ids.tracing: hash-baceacd472f83bb3307f19ab73e25b150c1fdc48c39f90126a9af7f9596fa089
- obj.clause-number: 6.2.2
- obj.element-name: note
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
- cross-reference -> prov-7104561-f118db89e55047b

#### prov-7104561-1214ddad492e4fb: Schaum (heading)
- bib.al.original-language: en
- bib.dp.publication-date: 2018-07-01
- ids.document: 7104561
- ids.element: section_6.2.3
- ids.language-synoptic: section_6.2.3
- ids.tracing: hash-16f40fd549fb92a43aad801c3a6457a41a0c56e10399233dc6be63992d6d7159
- obj.clause-number: 6.2.3
- obj.element-name: heading
- obj.language: de
- obj.specobject-type: heading
- ChapterName: 6.2.3 Schaum

##### tr--570aeb71-321d-47c4-82c1-10e363247405--enCJ7YA3DQXB: Schaum (provision)
Für den Einsatz von Schaum gilt Tabelle 6.
- bib.al.original-language: en
- bib.dp.publication-date: 2018-07-01
- ids.document: 7104561
- ids.element: section_6.2.3
- ids.language-synoptic: section_6.2.3
- ids.tracing: hash-ebed72a7601779cb248da66668879a7ac216f64877856412b50068e9ef95f2d1
- obj.clause-number: 6.2.3
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-7104561-286c2354700d493

##### prov-7104561-286c2354700d493: Löschschaum nach DIN EN 1568 (alle Teile) (provision)
Tabelle 6 — Löschschaum nach DIN EN 1568 (alle Teile)
| Lfd.Nr. | Geräte/ Anwendungsform | Wirksame Wurfweite (Mittelwert) m | Eignung für Brandklasse nach DIN EN 2^a | Mindestabstände (m) zwischen Löschmittelaustrittsöffnung und unter Spannung stehenden Anlagenteilen |  |  |  |  |
| --- | --- | --- | --- | --- | --- | --- | --- | --- |
| Lfd.Nr. | Geräte/ Anwendungsform | Wirksame Wurfweite (Mittelwert) m | Eignung für Brandklasse nach DIN EN 2^a | Niederspannung bis | Hochspannung bis AC |  |  |  |
| Lfd.Nr. | Geräte/ Anwendungsform | Wirksame Wurfweite (Mittelwert) m | Eignung für Brandklasse nach DIN EN 2^a | AC 1 000 V oder DC 1 500 V | 30 kV | 110 kV | 220 kV | 380 kV |
| 1 | Tragbare oder fahrbare Feuerlöscher, die die Anforderungen nach DIN EN 3-7:2007-10, Abschnitt 9 erfüllen | 2 bis 6 | A, B | 1 |  |  |  |  |
| 2 | Tragbare oder fahrbare Feuerlöscher, die die Anforderungen nach DIN EN 3-7:2007-10, Abschnitt 9 nicht erfüllen | 2 bis 6 | A, B |  | Einsatz nur in spannungsfreien Anlagenteilen |  |  |  |
| 3 | Sonstige Geräte, z. B. typgeprüfte tragbare Feuerlöscher oder typgeprüfte fahrbare Feuerlöscher | 3 bis 7 | A, B | 3^b |  |  |  |  |
| 4 | Tragbare Schaumstrahlrohre nach DIN EN 16712-3:2015-12 S1/S2/S4/S8 M0,5/M1/M2/M4/M8 | 9/12/20/25 3/4/6/7/10 | A, B A, B |  |  |  |  |  |
| 5 | Schaumstrahlrohre für Werfer-Unterteile nach DIN 14366-2:1984-10 SW10/SW20/SW40 | 35/45/65 | A, B |  |  |  |  |  |
|  | Bei Abgabe von Druckluftschaum: Strahlrohre nach DIN 14365-1:1991-02 oder DIN EN 15182 oder andere Strahlrohre mit Austrittsöffnungen ≤ 25 mm Durchmesser (für alle Strahlrohre gilt: ≤ 235 l/min Wasser-Schaummittelgemisch und C-Kupplung) |  | A, B |  |  |  |  |  |
| 6a | Sprühstrahl | 3 bis 5 |  | 1 |  |  |  |  |
| 6b | Vollstrahl | > 10 |  | 5 |  |  |  |  |
| ^a Die Eignung kann auch die Brandklasse F umfassen. ^b Dies gilt nur für den Einsatz typgeprüfter Löschgeräte und deren Verwendung in elektrischen Anlagen. |  |  |  |  |  |  |  |  |
| Gefahrenhinweise/Einsatzbeschränkungen Eine Gefahr besteht, wenn zwischen der Einsatzkraft und einem unter Spannung stehenden Anlagenteil eine durchgehende Verbindung aus Wasser und/oder Schaum besteht. Niederspannungsanlagen: 1. Schaum: darf grundsätzlich nur in spannungsfreien Anlagen eingesetzt werden; erforderlichenfalls sind auch benachbarte Anlagen spannungsfrei zu machen. Ausgenommen von dieser Beschränkung ist der Einsatz typgeprüfter Löschgeräte und deren Verwendung in elektrischen Anlagen. 2. Druckluftschaum: - keine Gefahr über den Löschmittelstrahl besteht, wenn die Mindestabstände in Zeile 6 eingehalten werden, - anhaftender Schaum an unter Spannung stehenden Teilen führt zu Spannungsverschleppungen, und die Einsatzkräfte können über einen damit in Verbindung stehenden Schaumteppich gefährdet werden (siehe Bild 2). Hochspannungsanlagen: Schaum darf ohne Ausnahmen nur bei spannungsfreien Anlagenteilen eingesetzt werden; erforderlichenfalls sind auch benachbarte Anlagenteile spannungsfrei zu machen, denn es besteht ansonsten die Gefahr der explosionsartigen Zerstörung der elektrischen Anlage (einhergehend mit z. B. herumfliegenden Teilen und Druckwellen) mit zusätzlicher Gefährdung der Einsatzkräfte. |  |  |  |  |  |  |  |  |
- bib.al.original-language: en
- bib.dp.publication-date: 2018-07-01
- ids.document: 7104561
- ids.element: table_6
- ids.language-synoptic: table_6
- ids.tracing: hash-69e24773ea33b7e7a138dc2ac3315000e6a41b945ff83711be44a066ec53eca4
- obj.clause-number: Tabelle 6
- obj.element-name: table
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-7104561-9b603ff400844d4

##### prov-7104561-9b603ff400844d4: Schaum (provision)
Bild 2 — Gefährdung der Einsatzkraft durch Spannungsverschleppung über Schaumteppich
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Legende
- bib.al.original-language: en
- bib.dp.publication-date: 2018-07-01
- ids.document: 7104561
- ids.element: section_6.2.3
- ids.language-synoptic: section_6.2.3
- ids.tracing: hash-1d612162f99eb0e144b2c19dea0560362e2f6c7eb553ebaa5c3e553bed1b2e50
- obj.clause-number: 6.2.3
- obj.element-name: figure
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-1b0d1bf147124c6: Pulver (heading)
- bib.al.original-language: en
- bib.dp.publication-date: 2018-07-01
- ids.document: 7104561
- ids.element: section_6.2.4
- ids.language-synoptic: section_6.2.4
- ids.tracing: hash-1c1f5a71ea64a193b59811ed95b687d0a3267ce12e076b588e0c1663e826fcdf
- obj.clause-number: 6.2.4
- obj.element-name: heading
- obj.language: de
- obj.specobject-type: heading
- ChapterName: 6.2.4 Pulver

##### tr--570aeb71-321d-47c4-82c1-10e363247405--ua7LGkmimR6h: Pulver (provision)
Für den Einsatz von Pulver gilt Tabelle 7.
- bib.al.original-language: en
- bib.dp.publication-date: 2018-07-01
- ids.document: 7104561
- ids.element: section_6.2.4
- ids.language-synoptic: section_6.2.4
- ids.tracing: hash-db761a4d2ef21adb5d08567a3326f4f385aa72b5dab04b2b5fc0f9daee61b72d
- obj.clause-number: 6.2.4
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-7104561-d8bfa09646f9424

##### prov-7104561-d8bfa09646f9424: Löschpulver nach DIN EN 615 (provision)
Tabelle 7 — Löschpulver nach DIN EN 615
| Lfd.Nr. | Geräte/ Anwendungsform | Wirksame Wurfweite (Mittelwert) m | Eignung für Brandklasse nach DIN EN 2 | Mindestabstände (m) zwischen Löschmittelaustrittsöffnung und unter Spannung stehenden Anlagenteilen |  |  |  |  |
| --- | --- | --- | --- | --- | --- | --- | --- | --- |
| Lfd.Nr. | Geräte/ Anwendungsform | Wirksame Wurfweite (Mittelwert) m | Eignung für Brandklasse nach DIN EN 2 | Niederspannung bis | Hochspannung bis AC |  |  |  |
| Lfd.Nr. | Geräte/ Anwendungsform | Wirksame Wurfweite (Mittelwert) m | Eignung für Brandklasse nach DIN EN 2 | AC 1 000 V oder DC 1 500 V | 30 kV | 110 kV | 220 kV | 380 kV |
| 1 | Tragbare Feuerlöscher nach DIN EN 3 (alle Teile) |  | B, C | 1 | 3^a | 3 | 4 | 5 |
| 1 | Tragbare Feuerlöscher nach DIN EN 3 (alle Teile) | 2 bis 6 | A, B, C | 1 | Einsatz nur in spannungsfreien Anlagenteilen |  |  |  |
| 1 | Tragbare Feuerlöscher nach DIN EN 3 (alle Teile) | 0 bis 1 | D | 1 | Einsatz nur in spannungsfreien Anlagenteilen |  |  |  |
| 2 | Sonstige Geräte, z. B. fahrbare Feuerlöscher | 6 bis 10 | B, C | 1 | 3^a | 3 | 4 | 5 |
| 2 | Sonstige Geräte, z. B. fahrbare Feuerlöscher |  | A, B, C | 1 | Einsatz nur in spannungsfreien Anlagenteilen |  |  |  |
| ^a Bei Aufsicht durch elektrotechnisch unterwiesene Personen oder Elektrofachkräfte ist ein Mindestabstand von 2 m zulässig. |  |  |  |  |  |  |  |  |
| Gefahrenhinweise/Einsatzbeschränkungen Der Einsatz von Löschpulver in elektrischen Anlagen und in deren Nähe darf nur mit Zustimmung des Anlagenbetreibers erfolgen. Beim Einsatz von Löschpulver ist zu beachten: Unter Einfluss von Temperatur, Nässe und Luftfeuchte können Löschpulverbeläge auf Isolatoren in einem Maße leitfähig werden, dass unter Einfluss höherer elektrischer Feldstärken, d. h. im Allgemeinen bei Hochspannung, kurzschlussartige Ströme zum Fließen kommen. Die dadurch entstehenden Störlichtbögen stellen eine Lebensgefahr für sich in der Nähe aufhaltende Personen und eine Gefährdung der Anlage dar. Aus diesem Grunde dürfen Löschpulver in Freiluft- und Innenraumanlagen nur angewendet werden, wenn diese Anlagen trocken sind. Die geforderten Mindestabstände zwischen Löschmittelaustrittsöffnung und unter Spannung stehenden Teilen der elektrischen Anlage dienen der Sicherheit des den Löscheinsatz durchführenden Personals vor direkten Stromeinwirkungen während des Löscheinsatzes. Leitfähige Beläge können in Hochspannungsanlagen Personen und die Anlagen selbst gefährden. Sie sind deshalb nach Möglichkeit zu vermeiden. Es sollten außerdem nur Löschpulver verwendet werden, die keine schwer zu reinigenden Beläge (z. B. Schmelzbeläge bei ABC-Pulver) auf den Anlagenteilen bilden. Der Einsatz von Löschpulver ist im Bereich staubempfindlicher Anlagen (wie Fernmeldeanlagen, Informationsverarbeitungsanlagen, Mess- und Regelanlagen, Verteilerschränken mit Schützen und Relais usw.) zu vermeiden. |  |  |  |  |  |  |  |  |
- bib.al.original-language: en
- bib.dp.publication-date: 2018-07-01
- ids.document: 7104561
- ids.element: table_7
- ids.language-synoptic: table_7
- ids.tracing: hash-0d94cc205994251978531d172d7414e8e393f897c7d12bd0ae42f23bc9c671f2
- obj.clause-number: Tabelle 7
- obj.element-name: table
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-16a41a8554b4444: Kohlenstoffdioxid (heading)
- bib.al.original-language: en
- bib.dp.publication-date: 2018-07-01
- ids.document: 7104561
- ids.element: section_6.2.5
- ids.language-synoptic: section_6.2.5
- ids.tracing: hash-26abfb1cdc00e256f802ab167dd70cbaa6116e519bceed6fe6d51fa6a12f7774
- obj.clause-number: 6.2.5
- obj.element-name: heading
- obj.language: de
- obj.specobject-type: heading
- ChapterName: 6.2.5 Kohlenstoffdioxid

##### tr--570aeb71-321d-47c4-82c1-10e363247405--tb5quOyzBDXA: Kohlenstoffdioxid (provision)
Für den Einsatz von Kohlenstoffdioxid gilt Tabelle 8.
- bib.al.original-language: en
- bib.dp.publication-date: 2018-07-01
- ids.document: 7104561
- ids.element: section_6.2.5
- ids.language-synoptic: section_6.2.5
- ids.tracing: hash-33d5f91fa7a02cda1828c3ff85127da9cd71a069fc32ccea54719e30ce4004fc
- obj.clause-number: 6.2.5
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-7104561-e1f4712221c14a5

##### prov-7104561-e1f4712221c14a5: Löschmittel Kohlenstoffdioxid (CO2) (provision)
Tabelle 8 — Löschmittel Kohlenstoffdioxid (CO_2)
| Lfd.Nr. | Geräte/ Anwendungsform | Wirksame Wurfweite (Mittelwert) m | Eignung für Brandklasse nach DIN EN 2 | Mindestabstände (m) zwischen Löschmittelaustrittsöffnung und unter Spannung stehenden Anlagenteilen |  |  |  |  |
| --- | --- | --- | --- | --- | --- | --- | --- | --- |
| Lfd.Nr. | Geräte/ Anwendungsform | Wirksame Wurfweite (Mittelwert) m | Eignung für Brandklasse nach DIN EN 2 | Niederspannung bis | Hochspannung bis AC |  |  |  |
| Lfd.Nr. | Geräte/ Anwendungsform | Wirksame Wurfweite (Mittelwert) m | Eignung für Brandklasse nach DIN EN 2 | AC 1 000 V oder DC 1 500 V | 30 kV | 110 kV | 220 kV | 380 kV |
| 1 | Tragbare Feuerlöscher nach DIN EN 3 (alle Teile) | 2 bis 3 | B | 1 | 3^a | 3 | 4 | 5 |
| 2 | Sonstige Geräte, z. B. fahrbare Feuerlöscher | 3 bis 4 | B |  |  |  |  |  |
| - a a Bei Aufsicht durch elektrotechnisch unterwiesene Personen oder Elektrofachkräfte ist ein Mindestabstand von 2 m zulässig. |  |  |  |  |  |  |  |  |
| Gefahrenhinweise/Einsatzbeschränkungen Kohlenstoffdioxid ist elektrisch nichtleitend und hinterlässt keine Rückstände. Die Anwendung ist bei unter Spannung stehenden Anlagen unbedenklich, wenn die Mindestabstände eingehalten werden. Kohlenstoffdioxid ist schwerer als Luft, ist ab 5 % Volumenanteilen gesundheitsgefährdend und wirkt ab 8 % lebensbedrohlich. Vorsicht bei Verwendung in engen, schlecht belüfteten Räumen. Lebensgefahr! Gefahrenhinweise auf den Löschgeräten beachten. In Außenanlagen ist die Wirkung begrenzt, weil sich Kohlenstoffdioxid verflüchtigt. |  |  |  |  |  |  |  |  |
- bib.al.original-language: en
- bib.dp.publication-date: 2018-07-01
- ids.document: 7104561
- ids.element: table_8
- ids.language-synoptic: table_8
- ids.tracing: hash-6a792c51abe3c1fa974c046ea7fd5f1f7af941452e632547b236092a311ec692
- obj.clause-number: Tabelle 8
- obj.element-name: table
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

## prov-7104561-b3366865b9c44c6: Maßnahmen nach einem Brand (heading)
- bib.al.original-language: en
- bib.dp.publication-date: 2018-07-01
- ids.document: 7104561
- ids.element: section_7
- ids.language-synoptic: section_7
- ids.tracing: hash-0b936ed7209a98488fa78a33f6026091aa97be6f34e2228574953a24907af8c2
- obj.clause-number: 7
- obj.element-name: heading
- obj.language: de
- obj.specobject-type: heading
- ChapterName: 7 Maßnahmen nach einem Brand

### prov-7104561-76d17f6e6e53468: 7.1 (heading)
- bib.al.original-language: en
- bib.dp.publication-date: 2018-07-01
- ids.document: 7104561
- ids.element: section_7.1
- ids.language-synoptic: section_7.1
- ids.tracing: hash-82e806d7851d70e33296afeb44d32a45ec292c80ea4f84d41a2c69d16d46ca8f
- obj.element-name: heading
- obj.language: de
- obj.specobject-type: heading

#### tr--570aeb71-321d-47c4-82c1-10e363247405--UJjfQ60sRhO0 (provision)
Beim Betreten der Brandstelle ist besondere Vorsicht erforderlich.
- bib.al.original-language: en
- bib.dp.publication-date: 2018-07-01
- ids.document: 7104561
- ids.element: section_7.1
- ids.language-synoptic: section_7.1
- ids.tracing: hash-470d047414366e536b04d00e49f7409361a574c255a00149c58e58e721a85c58
- obj.clause-number: 7.1
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-86a83f94c3c94c1: 7.2 (heading)
- bib.al.original-language: en
- bib.dp.publication-date: 2018-07-01
- ids.document: 7104561
- ids.element: section_7.2
- ids.language-synoptic: section_7.2
- ids.tracing: hash-7994864c178d219669b2721a7838b1eed509b2b03b675e758c0e9dc2f6cce3a0
- obj.element-name: heading
- obj.language: de
- obj.specobject-type: heading

#### tr--570aeb71-321d-47c4-82c1-10e363247405--NkJ9qLyUdXOZ (provision)
Es besteht die Gefahr, dass vorhandene Metallteile unter Spannung stehen können, also nicht nur elektrische Leitungen und Geräte, sondern auch metallene Rohrleitungen, Dachrinnen oder Drahtzäune, sofern sie mit unter Spannung stehenden Anlagenteilen in Berührung stehen.
- bib.al.original-language: en
- bib.dp.publication-date: 2018-07-01
- ids.document: 7104561
- ids.element: section_7.2
- ids.language-synoptic: section_7.2
- ids.tracing: hash-b42c504e302e5ebcb51a4bff83c27fc953d8b82f00e95f8936709aea0075a65a
- obj.clause-number: 7.2
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-9ed550c1bd224ce: 7.3 (heading)
- bib.al.original-language: en
- bib.dp.publication-date: 2018-07-01
- ids.document: 7104561
- ids.element: section_7.3
- ids.language-synoptic: section_7.3
- ids.tracing: hash-0700df9e8c865fc633ccc9468ba405ad31d502c576c3fa0eaec2642c6f5c996d
- obj.element-name: heading
- obj.language: de
- obj.specobject-type: heading

#### tr--570aeb71-321d-47c4-82c1-10e363247405--honsdu3ANzHk (provision)
Nach dem Brand ist der Brandraum zu lüften, bevor Personen ohne Atemschutz den Raum betreten, wobei zu vermeiden ist, dass sich giftige und korrosive Zersetzungsprodukte im Gebäude ausbreiten (siehe 5.1.7).
- bib.al.original-language: en
- bib.dp.publication-date: 2018-07-01
- ids.document: 7104561
- ids.element: section_7.3
- ids.language-synoptic: section_7.3
- ids.tracing: hash-e2edbfe8d8ef426d8ea0382730b1b53dfda09e2c5170b867928e7577398d0617
- obj.clause-number: 7.3
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-7104561-b3fe32a1dc1c4f9

#### tr--570aeb71-321d-47c4-82c1-10e363247405--0ddhcYChexsA (provision)
Unbefugte Personen dürfen die Brandstelle nicht betreten.
- bib.al.original-language: en
- bib.dp.publication-date: 2018-07-01
- ids.document: 7104561
- ids.element: section_7.3
- ids.language-synoptic: section_7.3
- ids.tracing: hash-9fb932f2453bcd31816521d757e7e7e8538e4556949a884acb07844b73ef5e53
- obj.clause-number: 7.3
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-f48c2cb79f8141b: 7.4 (heading)
- bib.al.original-language: en
- bib.dp.publication-date: 2018-07-01
- ids.document: 7104561
- ids.element: section_7.4
- ids.language-synoptic: section_7.4
- ids.tracing: hash-9f32b8e40ba4621a6095c21c7f2a257f4389c701ba8fa80bb27034b677cdbb8d
- obj.element-name: heading
- obj.language: de
- obj.specobject-type: heading

#### tr--570aeb71-321d-47c4-82c1-10e363247405--8yK5chKWFkrL (provision)
Besteht Verdacht, dass Personen mit giftigen Zersetzungsprodukten in Kontakt gekommen sind, müssen sie unverzüglich fachärztlicher Betreuung zugeführt werden.
- bib.al.original-language: en
- bib.dp.publication-date: 2018-07-01
- ids.document: 7104561
- ids.element: section_7.4
- ids.language-synoptic: section_7.4
- ids.tracing: hash-48a40f6383dbc33e0ab749d0ffb5d9d2243e26356d24e76e595136a1a837776b
- obj.clause-number: 7.4
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-2fe8792393b9456: 7.5 (heading)
- bib.al.original-language: en
- bib.dp.publication-date: 2018-07-01
- ids.document: 7104561
- ids.element: section_7.5
- ids.language-synoptic: section_7.5
- ids.tracing: hash-1c050eabf224307be845cfc15e256b12ffddedd083e7fa56569d243fc0265c78
- obj.element-name: heading
- obj.language: de
- obj.specobject-type: heading

#### tr--570aeb71-321d-47c4-82c1-10e363247405--b1kcXynJAKEj (provision)
Unter Spannung stehende elektrische Anlagenteile sind gegen direktes Berühren zu sichern, siehe DIN VDE 0105-100 (VDE 0105-100) .
- bib.al.original-language: en
- bib.dp.publication-date: 2018-07-01
- ids.document: 7104561
- ids.element: section_7.5
- ids.language-synoptic: section_7.5
- ids.tracing: hash-2d2411853ed796090fe94b1fd6bf604b8a4ccd82bf1fe87f2ccd8f30b2fb879c
- obj.clause-number: 7.5
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-5eb9c89a2ce243c: 7.6 (heading)
- bib.al.original-language: en
- bib.dp.publication-date: 2018-07-01
- ids.document: 7104561
- ids.element: section_7.6
- ids.language-synoptic: section_7.6
- ids.tracing: hash-745b2a96bd50ca29850ff4e44bc4a52b898ab18ded81412d8ff645ca0a8e2238
- obj.element-name: heading
- obj.language: de
- obj.specobject-type: heading

#### tr--570aeb71-321d-47c4-82c1-10e363247405--Pw9Vr8YskUjX (provision)
Pulverbeläge auf Isolatoren können zu Schäden führen und sollten möglichst bald nach Beendigung der Löscharbeiten beseitigt werden.
- bib.al.original-language: en
- bib.dp.publication-date: 2018-07-01
- ids.document: 7104561
- ids.element: section_7.6
- ids.language-synoptic: section_7.6
- ids.tracing: hash-f821ec19256f363e3a4f16ffe1afbbb44290cc92d271f5ebd9f1d7d3da5a3721
- obj.clause-number: 7.6
- obj.element-name: paragraph
- obj.language: de
- obj.modality: recommendation
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-0f66ccc336ae459: 7.7 (heading)
- bib.al.original-language: en
- bib.dp.publication-date: 2018-07-01
- ids.document: 7104561
- ids.element: section_7.7
- ids.language-synoptic: section_7.7
- ids.tracing: hash-6f6307bd6ce3399fa2646c054e9fec9f8f173c38c58b9216859c31628dc1fb9c
- obj.element-name: heading
- obj.language: de
- obj.specobject-type: heading

#### tr--570aeb71-321d-47c4-82c1-10e363247405--VnqIWxJzvj44 (provision)
Die Freigabe oder gegebenenfalls die Wiederinbetriebnahme elektrischer Anlagen darf in Hochspannungsanlagen nur durch den Anlagenverantwortlichen erfolgen.
- bib.al.original-language: en
- bib.dp.publication-date: 2018-07-01
- ids.document: 7104561
- ids.element: section_7.7
- ids.language-synoptic: section_7.7
- ids.tracing: hash-fda569548b421e1a093c48bd4db97804879f8733db02125ab0fd489be14d07ef
- obj.clause-number: 7.7
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

## prov-7104561-9555d1e6324b425: Erste Maßnahmen bei Unfällen durch elektrischen Strom (heading)
- bib.al.original-language: en
- bib.dp.publication-date: 2018-07-01
- ids.document: 7104561
- ids.element: section_8
- ids.language-synoptic: section_8
- ids.tracing: hash-82ec50c8329511719a70e72774bad783ffe7c44cd63acf4fc334944603bc2ed9
- obj.clause-number: 8
- obj.element-name: heading
- obj.language: de
- obj.specobject-type: heading
- ChapterName: 8 Erste Maßnahmen bei Unfällen durch elektrischen Strom

### tr--570aeb71-321d-47c4-82c1-10e363247405--PbNaOnNkg5xw: Erste Maßnahmen bei Unfällen durch elektrischen Strom (provision)
Für Erste-Hilfe-Maßnahmen siehe DGUV Information 204-006 „Anleitung zur Ersten Hilfe“ und DGUV Fachinformation „Stromunfall - Ärztliche Vorstellung notwendig“.
- bib.al.original-language: en
- bib.dp.publication-date: 2018-07-01
- ids.document: 7104561
- ids.element: section_8
- ids.language-synoptic: section_8
- ids.tracing: hash-16a59d48afe48a4896d4b010680e8b517b0a60a9b7eace3b1d60ac883e682d6b
- obj.clause-number: 8
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-abd6ccbad9f545e: 8.1 (heading)
- bib.al.original-language: en
- bib.dp.publication-date: 2018-07-01
- ids.document: 7104561
- ids.element: section_8.1
- ids.language-synoptic: section_8.1
- ids.tracing: hash-a3a4ced7acce6d4eacf7c21f4474581d469c4fac3856876c58b07c69d34fe7cf
- obj.element-name: heading
- obj.language: de
- obj.specobject-type: heading

#### tr--570aeb71-321d-47c4-82c1-10e363247405--Eo0ga7tYAGpJ (provision)
Beim Berühren von unter Spannung stehenden Teilen besteht Lebensgefahr.
- bib.al.original-language: en
- bib.dp.publication-date: 2018-07-01
- ids.document: 7104561
- ids.element: section_8.1
- ids.language-synoptic: section_8.1
- ids.tracing: hash-e5c656980ca09274671afa107ec5586c15c291ef86afb2b754925eecdbd54051
- obj.clause-number: 8.1
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### tr--570aeb71-321d-47c4-82c1-10e363247405--xYJ3Rfrv680Z (provision)
Außer Verbrennungen kann der elektrische Strom eine Muskelverkrampfung, die zur Atemlähmung führen kann, und Herzkammerflimmern verursachen.
- bib.al.original-language: en
- bib.dp.publication-date: 2018-07-01
- ids.document: 7104561
- ids.element: section_8.1
- ids.language-synoptic: section_8.1
- ids.tracing: hash-2306508e407ef641be0a5ac526d5c00bdf3a35c7bb09fdc429de1d96d94da9f7
- obj.clause-number: 8.1
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### tr--570aeb71-321d-47c4-82c1-10e363247405--OPUX5Jtu5toi (provision)
Ein Verunglückter ist so schnell wie möglich von der Spannung zu trennen (siehe 8.2 und 8.3).
- bib.al.original-language: en
- bib.dp.publication-date: 2018-07-01
- ids.document: 7104561
- ids.element: section_8.1
- ids.language-synoptic: section_8.1
- ids.tracing: hash-2ba092debafb70a481a29795b6c1fe9836faada6396cab17220bd824649fca31
- obj.clause-number: 8.1
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-7104561-4228c1998a42440
- cross-reference -> prov-7104561-957557afbdb5435

### prov-7104561-4228c1998a42440: 8.2 (heading)
- bib.al.original-language: en
- bib.dp.publication-date: 2018-07-01
- ids.document: 7104561
- ids.element: section_8.2
- ids.language-synoptic: section_8.2
- ids.tracing: hash-a95d817fda61722181b168f8aa474bb72af6c9c193fdad204c2e6778441c06b5
- obj.element-name: heading
- obj.language: de
- obj.specobject-type: heading

#### tr--570aeb71-321d-47c4-82c1-10e363247405--EIPI2HUrVLDt (provision)
In Niederspannungsanlagen ist zunächst die betreffende Leitung spannungsfrei zu machen, da eine vorherige Berührung des Verunglückten den Helfer selbst gefährdet.
- bib.al.original-language: en
- bib.dp.publication-date: 2018-07-01
- ids.document: 7104561
- ids.element: section_8.2
- ids.language-synoptic: section_8.2
- ids.tracing: hash-45592cce02e564e031d4154ab912a306958fab95446fe74de7281d8f06cf61fc
- obj.clause-number: 8.2
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

#### tr--570aeb71-321d-47c4-82c1-10e363247405--TRRpAE0MBtNG (provision)
Ist dies nicht möglich, dann kann man den Verunglückten von gut isoliertem Standort aus (trockenes Holz, trockene Kleider) von den Leitungen oder Geräten wegziehen.
- bib.al.original-language: en
- bib.dp.publication-date: 2018-07-01
- ids.document: 7104561
- ids.element: section_8.2
- ids.language-synoptic: section_8.2
- ids.tracing: hash-8a961e547fcc146e6463283a9e68465d17735169eff32fc55d614402005eb6aa
- obj.clause-number: 8.2
- obj.element-name: paragraph
- obj.language: de
- obj.modality: permission
- obj.normativity: normative
- obj.specobject-type: provision
- obj.transformation-issues: Possibly wrong modal verb
- use.business-process: undefined
- use.business-sector: undefined
- use.interaction: undefined
- use.location: undefined
- use.product-category: undefined
- use.product-life-cycle: undefined
- use.project-phase: undefined
- use.purpose: undefined

#### tr--570aeb71-321d-47c4-82c1-10e363247405--oBWsoWRbGGQd (provision)
Dabei darf man unbedeckte Körperteile nicht mit ungeschützten Händen berühren, sondern muss sich z. B. trockener Decken, Kleider, Handschuhe, Holzlatten bedienen.
- bib.al.original-language: en
- bib.dp.publication-date: 2018-07-01
- ids.document: 7104561
- ids.element: section_8.2
- ids.language-synoptic: section_8.2
- ids.tracing: hash-9eb25e846e76d6680771f079e03dee995f2daad0f5cfead1968c7502891c6920
- obj.clause-number: 8.2
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-957557afbdb5435: 8.3 (heading)
- bib.al.original-language: en
- bib.dp.publication-date: 2018-07-01
- ids.document: 7104561
- ids.element: section_8.3
- ids.language-synoptic: section_8.3
- ids.tracing: hash-4d688b6398a1cbbac7b2703077353d062316ec0bbbed58737908cb016914d71c
- obj.element-name: heading
- obj.language: de
- obj.specobject-type: heading

#### tr--570aeb71-321d-47c4-82c1-10e363247405--cxow08hFUZQS (provision)
Bei Hochspannungsanlagen dürfen nur Elektrofachkräfte und elektrotechnisch unterwiesene Personen eingreifen.
- bib.al.original-language: en
- bib.dp.publication-date: 2018-07-01
- ids.document: 7104561
- ids.element: section_8.3
- ids.language-synoptic: section_8.3
- ids.tracing: hash-386fe01843a67cb4bd65e7665edc6b96966195f06374c4d054c94fc54201139e
- obj.clause-number: 8.3
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

#### tr--570aeb71-321d-47c4-82c1-10e363247405--M7oByMUsbOO7 (provision)
Auch die Annäherung (siehe 5.3.4 und 5.3.5) an den Verunglückten ist gefährlich.
- bib.al.original-language: en
- bib.dp.publication-date: 2018-07-01
- ids.document: 7104561
- ids.element: section_8.3
- ids.language-synoptic: section_8.3
- ids.tracing: hash-d2b13b9e04b4885b51a713dab3f547f2645919148b829cc2d3e7e61f38e9dd87
- obj.clause-number: 8.3
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-7104561-24000de83ed8423
- cross-reference -> prov-7104561-80f799700b314a0

### prov-7104561-e8b0c5844004409: 8.4 (heading)
- bib.al.original-language: en
- bib.dp.publication-date: 2018-07-01
- ids.document: 7104561
- ids.element: section_8.4
- ids.language-synoptic: section_8.4
- ids.tracing: hash-f01429ac30d99444ef6c16ea6605a9b5a8b6df97f9c9de31b3a7e714552ec852
- obj.element-name: heading
- obj.language: de
- obj.specobject-type: heading

#### tr--570aeb71-321d-47c4-82c1-10e363247405--1rtlk2EFnbVP (provision)
Brennende Personen sind am Fortlaufen zu hindern und notfalls am Boden zu wälzen.
- bib.al.original-language: en
- bib.dp.publication-date: 2018-07-01
- ids.document: 7104561
- ids.element: section_8.4
- ids.language-synoptic: section_8.4
- ids.tracing: hash-ca72ae5f6606e366fd9bf6fdf7a6abe78d7e9989719e349b6d798178a2c35128
- obj.clause-number: 8.4
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

#### tr--570aeb71-321d-47c4-82c1-10e363247405--eiBdSenpZcMl (provision)
Zum Ablöschen brennender Kleidung an Personen eignen sich insbesondere Wasser, Feuerlöscher oder Löschdecken.
- bib.al.original-language: en
- bib.dp.publication-date: 2018-07-01
- ids.document: 7104561
- ids.element: section_8.4
- ids.language-synoptic: section_8.4
- ids.tracing: hash-c2bf9d7cacff8f3e7e7abea902b03d5426f5b54eb7d3744a559456a9d4893eca
- obj.clause-number: 8.4
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### tr--570aeb71-321d-47c4-82c1-10e363247405--k6Y30Fit4kX6 (provision)
Auch das Einhüllen mit anderen Decken, ausgenommen brennbare Kunststoffdecken, kann helfen.
- bib.al.original-language: en
- bib.dp.publication-date: 2018-07-01
- ids.document: 7104561
- ids.element: section_8.4
- ids.language-synoptic: section_8.4
- ids.tracing: hash-ec2fe9ef9461a394f452e469c2c5aee54f34e72810a2a21de00a6a670f82a8db
- obj.clause-number: 8.4
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### tr--570aeb71-321d-47c4-82c1-10e363247405--i5hZkgmTwPfN (provision)
Es können auch andere Löschmittel eingesetzt werden, wenn nur damit schnell gelöscht werden kann, da dies als Rettungsmaßnahme Vorrang vor anderen Überlegungen haben muss.
- bib.al.original-language: en
- bib.dp.publication-date: 2018-07-01
- ids.document: 7104561
- ids.element: section_8.4
- ids.language-synoptic: section_8.4
- ids.tracing: hash-6cfd6fd99f4b1bba2b9f006389c1b2194aa40eb041b76ae518fb4f91fc38bafd
- obj.clause-number: 8.4
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

#### tr--570aeb71-321d-47c4-82c1-10e363247405--Dh21j02zhnnv (provision)
Wurden andere Löschmittel als Wasser eingesetzt, so ist dies dem erstversorgenden Arzt oder dem Rettungsdienstpersonal mitzuteilen.
- bib.al.original-language: en
- bib.dp.publication-date: 2018-07-01
- ids.document: 7104561
- ids.element: section_8.4
- ids.language-synoptic: section_8.4
- ids.tracing: hash-2e4217b458a671437e7ab2ee26483f05ae4dc4f57fdf945664364e2854761dc4
- obj.clause-number: 8.4
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

## prov-7104561-af1cd1edcd2042c: Beurteilung von Gefahren, die von PCB-haltigen Betriebsmitteln ausgehen können (heading)
- bib.al.original-language: en
- bib.dp.publication-date: 2018-07-01
- ids.document: 7104561
- ids.element: section_Anhang_A
- ids.language-synoptic: section_Anhang_A
- ids.tracing: hash-eb49fe1a02749be93d7ad6a059ee1131575d34f723bebd5ce807ebffd00381e9
- obj.clause-number: Anhang A
- obj.element-name: heading
- obj.language: de
- obj.specobject-type: heading
- ChapterName: Anhang A Beurteilung von Gefahren, die von PCB-haltigen Betriebsmitteln ausgehen können

### tr--570aeb71-321d-47c4-82c1-10e363247405--5Yqyg9HMMWnr: Beurteilung von Gefahren, die von PCB-haltigen Betriebsmitteln ausgehen können (provision)
Bei der Beurteilung der Gefahren, die von PCB-haltigen Betriebsmitteln ausgehen können, ist zu unterscheiden:
- Gefährlichkeit der polychlorierten Biphenyle (PCB) bei Brandeinwirkung.
Aus höher chlorierten Biphenylen können sich Spuren giftiger Zersetzungsprodukte bilden (Dibenzodioxin- und Dibenzofuran-Verbindungen).
Maßnahmen: Die Entstehung der Zersetzungsprodukte muss durch raschen und energischen Löschangriff, gegebenenfalls durch Kühlung der PCB-haltigen Betriebsmittel, vermieden werden. Dabei gewähren die Feuerwehreinsatzkleidung, umluftunabhängiger Atemschutz und Kontaminationsschutzhaube ausreichende Sicherheit für die Einsatzkräfte. Besondere Vollschutzanzüge sind unter anderem wegen ihrer geringen thermischen Widerstandsfähigkeit und vor allem wegen der physiologischen Belastung des Personals bei Brandbekämpfung im Innenangriff ungeeignet.
- Gefährlichkeit der polychlorierten Biphenyle (PCB) ohne Brandeinwirkung.
PCB sind nach der Gefahrstoffverordnung als gesundheitsschädlich und umweltgefährdend eingestuft (Andreaskreuz, Xn, N bzw. GHS 08). Wegen ihrer hohen Stabilität sind sie jedoch schwer abbaubar, sie dürfen daher nicht ins Erdreich gelangen.
Maßnahmen: Ausgelaufene Flüssigkeit ist in Behältern aufzufangen oder mit Bindemitteln aufzunehmen und als gefährlicher Abfall zu entsorgen. Es sind Chemikalienschutzhandschuhe zu tragen, gegebenenfalls ist Atemschutz anzulegen; Hautkontakt ist zu vermeiden.
- Waren beim Brand PCB-haltige Betriebsmittel (siehe 4.1.2) beteiligt, ist die Brandstelle zu sperren und zu sichern. Schutzkleidung der Einsatzkräfte und Geräte, die im Einsatz waren, sind an einem Sammelplatz zu lagern. Weitere Maßnahmen sind abhängig von dem Ergebnis der Kontaminationsprüfung.
- bib.al.original-language: en
- bib.dp.publication-date: 2018-07-01
- ids.document: 7104561
- ids.element: section_Anhang_A
- ids.language-synoptic: section_Anhang_A
- ids.tracing: hash-381481c124b64cc1c26bc357ffccd01ade5d5f6f580415a070a8d0b580cd1f85
- obj.clause-number: Anhang A
- obj.element-name: paragraph
- obj.language: de
- obj.modality: requirement
- obj.normativity: informative
- obj.specobject-type: provision
- use.business-process: undefined
- use.business-sector: undefined
- use.interaction: undefined
- use.location: undefined
- use.product-category: undefined
- use.product-life-cycle: undefined
- use.project-phase: undefined
- use.purpose: undefined
- cross-reference -> prov-7104561-dbbfaa73d01043a

## prov-7104561-f118db89e55047b: Erläuterungen (heading)
- bib.al.original-language: en
- bib.dp.publication-date: 2018-07-01
- ids.document: 7104561
- ids.element: section_Anhang_B
- ids.language-synoptic: section_Anhang_B
- ids.tracing: hash-e7595718a4331350a8534ea75edde90c75bf7dbcc80efd6cf9c4a920221b2b1d
- obj.clause-number: Anhang B
- obj.element-name: heading
- obj.language: de
- obj.specobject-type: heading
- ChapterName: Anhang B Erläuterungen

### tr--570aeb71-321d-47c4-82c1-10e363247405--1MyIORXmOVxX: Erläuterungen (provision)
– Zu Tabelle 1, PV-Anlagen:
Der Aussage, es tritt durch Mondlicht oder künstliches Licht keine elektrische Gefährdung auf, liegen insbesondere die Untersuchungen von Prof. Häberlin und G. Moine, A. M. Serve zugrunde (siehe Literaturhinweise).
- bib.al.original-language: en
- bib.dp.publication-date: 2018-07-01
- ids.document: 7104561
- ids.element: section_Anhang_B
- ids.language-synoptic: section_Anhang_B
- ids.tracing: hash-a660316e7d7720addaae5f50f133a2e2f9e294e861b8d6e248215363d45e96bd
- obj.clause-number: Anhang B
- obj.element-name: paragraph
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
- cross-reference -> prov-7104561-732b03c7ffc84bc

### tr--570aeb71-321d-47c4-82c1-10e363247405--jr9GZ7P1Rpb6: Erläuterungen (provision)
Es treten keine lebensbedrohlichen Ströme auf.
- bib.al.original-language: en
- bib.dp.publication-date: 2018-07-01
- ids.document: 7104561
- ids.element: section_Anhang_B
- ids.language-synoptic: section_Anhang_B
- ids.tracing: hash-826a9b2fe9b3d5eddd63360dd0e3dbdb41a3e0eb122004212aaf1c7e2c613c03
- obj.clause-number: Anhang B
- obj.element-name: paragraph
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### tr--570aeb71-321d-47c4-82c1-10e363247405--CrwczexXMFd4: Erläuterungen (provision)
Eine Körperdurchströmung kann zudem nur auftreten, wenn die Einsatzkraft beide Pole des PV-Generators gleichzeitig berührt.
- bib.al.original-language: en
- bib.dp.publication-date: 2018-07-01
- ids.document: 7104561
- ids.element: section_Anhang_B
- ids.language-synoptic: section_Anhang_B
- ids.tracing: hash-1732b2d7962dc75f7072c2d55648e6f9d15154dafac84a6ade8b85522b8b2f94
- obj.clause-number: Anhang B
- obj.element-name: paragraph
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### tr--570aeb71-321d-47c4-82c1-10e363247405--He2teGmSgM7C: Erläuterungen (provision)
– Zu Tabelle 5:
Die Vergrößerung der Mindestabstände für Strahlrohre DIN 14365-BM wurde der Einfachheit halber geändert.
- bib.al.original-language: en
- bib.dp.publication-date: 2018-07-01
- ids.document: 7104561
- ids.element: section_Anhang_B
- ids.language-synoptic: section_Anhang_B
- ids.tracing: hash-96a5c15cae7e1340e34bebd8533492dbc00703364eeb7232cd10e832fc455966
- obj.clause-number: Anhang B
- obj.element-name: paragraph
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
- cross-reference -> prov-7104561-69867da9b1324e0

### tr--570aeb71-321d-47c4-82c1-10e363247405--awHm8W30avfo: Erläuterungen (provision)
Der Änderung lagen die Angaben der DIN VDE 0132 (VDE 0132):2001-08 zugrunde, wonach sich der Mindestabstand um 0,75 m für jeden Millimeter, um den sich der Mundstück- bzw. der Düsendurchmesser zwischen 12 mm und 22 mm vergrößert, und in Hochspannungsanlagen um zusätzlich 2 m vergrößert.
- bib.al.original-language: en
- bib.dp.publication-date: 2018-07-01
- ids.document: 7104561
- ids.element: section_Anhang_B
- ids.language-synoptic: section_Anhang_B
- ids.tracing: hash-79ccae1acde138e4fec4b1b740f70aea6779d6e41fe6016d759a39647ba271aa
- obj.clause-number: Anhang B
- obj.element-name: paragraph
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### tr--570aeb71-321d-47c4-82c1-10e363247405--JV85OQPZyIZF: Erläuterungen (provision)
Geringere Abstände haben bei Einsätzen, in denen Strahlrohre DIN 14365-BM zur Anwendung kommen, praktisch keine Bedeutung.
- bib.al.original-language: en
- bib.dp.publication-date: 2018-07-01
- ids.document: 7104561
- ids.element: section_Anhang_B
- ids.language-synoptic: section_Anhang_B
- ids.tracing: hash-00bcdde65f0a599e887318e00f71df73d15a781d00944298f3aeaf79f9a82621
- obj.clause-number: Anhang B
- obj.element-name: paragraph
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### tr--570aeb71-321d-47c4-82c1-10e363247405--DDJ1LBrq1RJl: Erläuterungen (provision)
– Zur Verwendung von Hohlstrahlrohren nach DIN EN 15182-2:
Mit Druckluftschaum durchgeführte Versuche der vfdb (Vereinigung zur Förderung des deutschen Brandschutzes e. V.) in Kooperation mit DKE/K 213 haben ergeben, dass eine elektrische Gefährdung in Niederspannungsanlagen aufgrund der Zerfallslänge bei Abgabe über Strahlrohre mit einem maximalen Durchfluss von 235 l/min (siehe DIN EN 15182), die mit einer C-Kupplung nach DIN 14307 angeschlossen werden, nicht auftritt.
- bib.al.original-language: en
- bib.dp.publication-date: 2018-07-01
- ids.document: 7104561
- ids.element: section_Anhang_B
- ids.language-synoptic: section_Anhang_B
- ids.tracing: hash-7ed1622e1f278e04d5300d5b714611505e4a3622e5ed7b7ff7027e3b15beb8c6
- obj.clause-number: Anhang B
- obj.element-name: paragraph
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### tr--570aeb71-321d-47c4-82c1-10e363247405--nfXoe98qTwxF: Erläuterungen (provision)
Daher war es auch konsequent, die Tabelle 5 zur Verwendung mit „C“-Hohlstrahlrohren im Rahmen der Anpassung der Tabelle 6 mit anzupassen.
- bib.al.original-language: en
- bib.dp.publication-date: 2018-07-01
- ids.document: 7104561
- ids.element: section_Anhang_B
- ids.language-synoptic: section_Anhang_B
- ids.tracing: hash-fd6e982c32541558a6cb47f8727d015bbc2880169229a05adaafae2aabdf4131
- obj.clause-number: Anhang B
- obj.element-name: paragraph
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
- cross-reference -> prov-7104561-69867da9b1324e0
- cross-reference -> prov-7104561-286c2354700d493

### tr--570aeb71-321d-47c4-82c1-10e363247405--cyLqeg60FPPY: Erläuterungen (provision)
Gleichwohl wird aufgrund arbeitsschutzrechtlicher Anforderungen empfohlen, anstelle einer einzelfallbezogenen Gefährdungsbeurteilung zur Eignung der Strahlrohre durch den Unternehmer (hier: Feuerwehr) die elektrische Gefährdung im Vorfeld durch die Strahlrohrhersteller zu überprüfen (z. B. durch Messungen analog DIN 14365).
- bib.al.original-language: en
- bib.dp.publication-date: 2018-07-01
- ids.document: 7104561
- ids.element: section_Anhang_B
- ids.language-synoptic: section_Anhang_B
- ids.tracing: hash-3cf36e1f56f071cdc5e1b0acc1f07c089ff5acee2e37893bbc89801d36451ddc
- obj.clause-number: Anhang B
- obj.element-name: paragraph
- obj.language: de
- obj.modality: recommendation
- obj.normativity: informative
- obj.specobject-type: provision
- use.business-process: undefined
- use.business-sector: undefined
- use.interaction: undefined
- use.location: undefined
- use.product-category: undefined
- use.product-life-cycle: undefined
- use.project-phase: undefined
- use.purpose: undefined

### tr--570aeb71-321d-47c4-82c1-10e363247405--bMNqBlzJVXVN: Erläuterungen (provision)
– Zu Tabelle 6, Zur Verwendung von Schaum in Hochspannungsanlagen:
Durch Schaum werden die Isolationsstrecken beeinträchtigt.
- bib.al.original-language: en
- bib.dp.publication-date: 2018-07-01
- ids.document: 7104561
- ids.element: section_Anhang_B
- ids.language-synoptic: section_Anhang_B
- ids.tracing: hash-286dda569e558e9540f75d3cdb25c4c533afa90a235c8afe1e6d1c81ae73ec49
- obj.clause-number: Anhang B
- obj.element-name: paragraph
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
- cross-reference -> prov-7104561-286c2354700d493

### tr--570aeb71-321d-47c4-82c1-10e363247405--nDR9mMUFcohW: Erläuterungen (provision)
Dies kann zu Erd- und Kurzschlüssen führen, einhergehend mit explosionsartigen Zerstörungen der elektrischen Anlagen.
- bib.al.original-language: en
- bib.dp.publication-date: 2018-07-01
- ids.document: 7104561
- ids.element: section_Anhang_B
- ids.language-synoptic: section_Anhang_B
- ids.tracing: hash-28daae3c7adb60032291225303709a6e24fdb7c50fa589224e0a3861961268f4
- obj.clause-number: Anhang B
- obj.element-name: paragraph
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

## prov-7104561-434b6c56d0004cf: Literaturhinweise (heading)
- bib.al.original-language: en
- bib.dp.publication-date: 2018-07-01
- ids.document: 7104561
- ids.element: section_Literaturhinweise
- ids.language-synoptic: section_Literaturhinweise
- ids.tracing: hash-a3f8d6b76590ee9a04759989a2b330417089d0b9293dfb244959f204d3014efd
- obj.element-name: heading
- obj.language: de
- obj.specobject-type: heading

### prov-7104561-d6c9cb8546c84cc: Literaturhinweise (provision)
- Verordnung über Sicherheits- und Gesundheitsschutz bei der Bereitstellung von Arbeitsmitteln und deren Benutzung bei der Arbeit, über Sicherheit beim Betrieb überwachungsbedürftiger Anlagen und über die Organisation des betrieblichen Arbeitsschutzes (Betriebssicherheitsverordnung – BetrSichV)
- DGUV Information 204-006 (BGI/GUV-I 503):2011, Information – Anleitung zur Ersten Hilfe
- DGUV Information 203-052 (BGI/GUV-I 8677):2011, Information – Elektrische Gefahren an der Einsatzstelle – Vortrag für Einsatzkräfte
- DGUV Information 200-005 (BGI/GUV-I 8686):2012, Information – Qualifizierung für Arbeiten an Fahrzeugen mit Hochvoltsystemen
- DGUV Vorschrift 1 (BGV A1) (GUV-V A1):2013, Unfallverhütungsvorschrift – Grundsätze der Prävention
- GUV-V C53 (DGUV Vorschrift 49):2005, Unfallverhütungsvorschrift „Feuerwehren“ mit Durchführungsanweisungen
- Verordnung zum Schutz vor Gefahrstoffen (Gefahrstoffverordnung – GefStoffV)
- Häberlin, H., Borgna, L., Schärf, P., PV und Feuerwehr: Keine Panik, realistische Einschätzung der elektrischen Gefahren und möglicher Gegenmaßnahmen, 26. Symposium Photovoltaische Solarenergie Staffelstein, 2011
- Moine, G., Serve, A. M., Campagne de tests Nocturnes sur la Plateforme Photovoltaique Qualiphoton de Transenergie, veröffentlicht durch Direction de la Sécurité Civile (DSC), Syndicat des Energies Renouvables, Transenergie
- bib.al.original-language: en
- bib.dp.publication-date: 2018-07-01
- ids.document: 7104561
- ids.element: section_Literaturhinweise
- ids.language-synoptic: section_Literaturhinweise
- ids.tracing: hash-423ed117c33f7c208c8abd0455bc666df1d50e4157c44a3ad5209be25a82ef4c
- obj.element-name: list-of-documents
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
