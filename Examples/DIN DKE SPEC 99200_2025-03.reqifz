# DIN DKE SPEC 99200:2025-03

# Specification: DIN DKE SPEC 99200:2025-03
- bib.al.original-language: en
- bib.dp.publication-date: 2025-03-01
- bib.ti.title-english: ReqIF™-Interpretation für öffentliche Normen - Release 1.3; Text Englisch
- bib.ts.document-type: undefined
- ids.document: 99200
- obj.language: en
- pub.harmonization: IDiS ReqIF interpretation for public standards 1.3
- pub.sales-number: 0110012
- pub.software: VDE CaaS 0.1.6
- pub.supplier: VDE
- pub.transformation-date: 2026-08-04T10:04:12.631378184Z
- pub.url: https://[changeme].dke.de/api/publications/99200/reqif

## pkn--99200: ReqIF™-Interpretation für öffentliche Normen - Release 1.3; Text Englisch (document)
DIN DKE SPEC 99200:2025-03
- bib.al.original-language: en
- bib.dp.publication-date: 2025-03-01
- bib.ts.document-type: undefined
- ids.document: 99200
- obj.language: en
- obj.specobject-type: document
- pub.harmonization: IDiS ReqIF interpretation for public standards 1.3
- pub.sales-number: 0110012
- pub.software: VDE CaaS 0.1.6
- pub.supplier: VDE
- pub.transformation-date: 2026-08-04T10:04:12.631378184Z
- pub.url: https://[changeme].dke.de/api/publications/99200/reqif

## prov-100000012-4bca88e60f4a47d: Contents (heading)
- bib.al.original-language: en
- bib.dp.publication-date: 2025-03-01
- ids.document: 99200
- ids.element: o1749224057159-e1
- ids.language-synoptic: o1749224057159-e1
- ids.tracing: hash-0141d498db95de8bdde216856de1865c9dc4bb6175d0ff78868e6cf58cc22538
- obj.element-name: heading
- obj.language: en
- obj.specobject-type: heading

## prov-100000012-5a6c949ce635451: Foreword (heading)
- bib.al.original-language: en
- bib.dp.publication-date: 2025-03-01
- ids.document: 99200
- ids.element: o1749224057161-foreword.nat
- ids.language-synoptic: o1749224057161-foreword.nat
- ids.tracing: hash-954293da5a944b6c748931d59dadde3e2c0ad27cd26bd8c629ebfe67e8cb316d
- obj.element-name: heading
- obj.language: en
- obj.specobject-type: heading

### tr--6d400e6f-d82a-44a1-8922-1185ec080fbf--KCP5cWAyxexl: Foreword (provision)
This DIN DKE SPEC has been developed according to the PAS procedure.
- bib.al.original-language: en
- bib.dp.publication-date: 2025-03-01
- ids.document: 99200
- ids.element: o1749224057161-foreword.nat
- ids.language-synoptic: o1749224057161-foreword.nat
- ids.tracing: hash-1c7f5afa4a9f115ad70a21cf0f519224072f8decbec8f26f3203feccb0834c5b
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### tr--6d400e6f-d82a-44a1-8922-1185ec080fbf--PDly2W99NYCL: Foreword (provision)
The development of a DIN SPEC according to the PAS procedure is carried out in DIN-SPEC-consortiums and does not require the participation of all stakeholders.
- bib.al.original-language: en
- bib.dp.publication-date: 2025-03-01
- ids.document: 99200
- ids.element: o1749224057161-foreword.nat
- ids.language-synoptic: o1749224057161-foreword.nat
- ids.tracing: hash-dc16d53e62241b45fcab15dbf8656039588efeb6409db25697e861e83bdbd3cd
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### tr--6d400e6f-d82a-44a1-8922-1185ec080fbf--k4Ko2Z4hUHQC: Foreword (provision)
This document has been developed and adopted by the initiator(s) and authors named below:
- Schaeffler Technologies AG & Co. KG
- Markus Franke
- Dietmar Lochner
- VDE Verband der Elektrotechnik Elektronik Informationstechnik e. V.
- Dirk Buchholz
- Siemens AG
- Heinz Dresbach
- DIN Solutions GmbH
- Andreas Wernicke
- bib.al.original-language: en
- bib.dp.publication-date: 2025-03-01
- ids.document: 99200
- ids.element: o1749224057161-foreword.nat
- ids.language-synoptic: o1749224057161-foreword.nat
- ids.tracing: hash-468b86f10fdb28ad20877c4627883c772dddbae47e34146e0bed97a3a1e85a19
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### tr--6d400e6f-d82a-44a1-8922-1185ec080fbf--SvHnGxQVUWE8: Foreword (provision)
At present, there are no standards covering this topic in the body of German Standards.
- bib.al.original-language: en
- bib.dp.publication-date: 2025-03-01
- ids.document: 99200
- ids.element: o1749224057161-foreword.nat
- ids.language-synoptic: o1749224057161-foreword.nat
- ids.tracing: hash-2df1f14448f2bb74542f80ea9ef40f303ca9b56e307d000e94c711c4f813ab0a
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### tr--6d400e6f-d82a-44a1-8922-1185ec080fbf--nxLhmmxDYnfd: Foreword (provision)
DIN DKE SPECs are not part of the body of German Standards.
- bib.al.original-language: en
- bib.dp.publication-date: 2025-03-01
- ids.document: 99200
- ids.element: o1749224057161-foreword.nat
- ids.language-synoptic: o1749224057161-foreword.nat
- ids.tracing: hash-841f901182a869b2ed0b0f5e8d754582e72d54c534004d2c99ea29f7eebda384
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### tr--6d400e6f-d82a-44a1-8922-1185ec080fbf--SrIfrafJTe6D: Foreword (provision)
A draft of this DIN DKE SPEC has not been published.
- bib.al.original-language: en
- bib.dp.publication-date: 2025-03-01
- ids.document: 99200
- ids.element: o1749224057161-foreword.nat
- ids.language-synoptic: o1749224057161-foreword.nat
- ids.tracing: hash-8c6620334aca3d104afba3a76c9e2a95a8218cbd3d7b0e52a6fcd8d8b970ed57
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### tr--6d400e6f-d82a-44a1-8922-1185ec080fbf--lu9STUuYPXGQ: Foreword (provision)
Despite great efforts to ensure the accuracy, reliability and precision of technical and non-technical information, the DIN-SPEC-consortium cannot give any explicit or implicit assurance or warranty in respect of the accuracy of the document.
- bib.al.original-language: en
- bib.dp.publication-date: 2025-03-01
- ids.document: 99200
- ids.element: o1749224057161-foreword.nat
- ids.language-synoptic: o1749224057161-foreword.nat
- ids.tracing: hash-7c5243fcf4697206042bb0c6d92e56bf03e881299c434f01bfb25f574054deaa
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### tr--6d400e6f-d82a-44a1-8922-1185ec080fbf--im2q3h5Wcim3: Foreword (provision)
Users of this document are hereby made aware that the consortium cannot be held liable for any damage or loss.
- bib.al.original-language: en
- bib.dp.publication-date: 2025-03-01
- ids.document: 99200
- ids.element: o1749224057161-foreword.nat
- ids.language-synoptic: o1749224057161-foreword.nat
- ids.tracing: hash-61d9193a8a3696f060ebff492bf7ad06016fdfa707151a411561c3e5f1127520
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### tr--6d400e6f-d82a-44a1-8922-1185ec080fbf--DadFJZOOpzpM: Foreword (provision)
The application of this DIN DKE SPEC does not release users from the responsibility for their own actions and is applied at their own risk.
- bib.al.original-language: en
- bib.dp.publication-date: 2025-03-01
- ids.document: 99200
- ids.element: o1749224057161-foreword.nat
- ids.language-synoptic: o1749224057161-foreword.nat
- ids.tracing: hash-d0078d292a3e2d8f73168f792a715b1965b6d6a5a4cbc12289086a3ed2bb090b
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### tr--6d400e6f-d82a-44a1-8922-1185ec080fbf--7EYubOfOEKuG: Foreword (provision)
Attention is drawn to the possibility that some of the elements of this document may be the subject of patent rights.
- bib.al.original-language: en
- bib.dp.publication-date: 2025-03-01
- ids.document: 99200
- ids.element: o1749224057161-foreword.nat
- ids.language-synoptic: o1749224057161-foreword.nat
- ids.tracing: hash-a179566fe6fee82443ad3c04df195df424d6e98d3e48f22a309e005e0f60e4d8
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### tr--6d400e6f-d82a-44a1-8922-1185ec080fbf--K09TuPNnOrbY: Foreword (provision)
DIN shall not be held responsible for identifying any or all such patent rights.
- bib.al.original-language: en
- bib.dp.publication-date: 2025-03-01
- ids.document: 99200
- ids.element: o1749224057161-foreword.nat
- ids.language-synoptic: o1749224057161-foreword.nat
- ids.tracing: hash-8a8139777daffd024cc329fbec6f18a820fb05f8c965b7f2b05eed2480f39490
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### tr--6d400e6f-d82a-44a1-8922-1185ec080fbf--EePVxEIyrrQM: Foreword (provision)
Provision of this document free of charge as a PDF via the DIN Media Webshop has been financed in advance.
- bib.al.original-language: en
- bib.dp.publication-date: 2025-03-01
- ids.document: 99200
- ids.element: o1749224057161-foreword.nat
- ids.language-synoptic: o1749224057161-foreword.nat
- ids.tracing: hash-575de52afa25f0cb0bc025f7ea9c7cedb16a2b46805a52481a7eed2a2f060328
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### tr--6d400e6f-d82a-44a1-8922-1185ec080fbf--ALAWNxAvg2N2: Foreword (provision)
For current information on this document, please go to DIN’s website (www.din.de) and search for the document number in question.
- bib.al.original-language: en
- bib.dp.publication-date: 2025-03-01
- ids.document: 99200
- ids.element: o1749224057161-foreword.nat
- ids.language-synoptic: o1749224057161-foreword.nat
- ids.tracing: hash-038960b43068ee908cf865329f2cba29e36a422f641850df67abf388f021c9fe
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

## prov-100000012-0714005b8c2840f: Introduction (heading)
- bib.al.original-language: en
- bib.dp.publication-date: 2025-03-01
- ids.document: 99200
- ids.element: o1749224057163-introduction.nat
- ids.language-synoptic: o1749224057163-introduction.nat
- ids.tracing: hash-7eec71258fe41a5eb5b616767b046554df97ad783f0f1888eb9e456096b4950e
- obj.element-name: heading
- obj.language: en
- obj.specobject-type: heading

### tr--6d400e6f-d82a-44a1-8922-1185ec080fbf--ViJY2HRu4N4s: Introduction (provision)
As standardization plays a fundamental role in the context of Industry 4.0, the publishers of technical and legislative regulations should drive forward the digital transformation in the interests of their stakeholders.
- bib.al.original-language: en
- bib.dp.publication-date: 2025-03-01
- ids.document: 99200
- ids.element: o1749224057163-introduction.nat
- ids.language-synoptic: o1749224057163-introduction.nat
- ids.tracing: hash-aa7866ed56670a7327fbc13e67528f6b655d8320fa3a86323510be296b2c3027
- obj.element-name: paragraph
- obj.language: en
- obj.modality: recommendation
- obj.normativity: normative
- obj.specobject-type: provision
- use.business-process: undefined
- use.business-sector: undefined
- use.interaction: undefined
- use.location: undefined
- use.product-category: undefined
- use.product-life-cycle: undefined
- use.project-phase: undefined
- use.purpose: undefined

### tr--6d400e6f-d82a-44a1-8922-1185ec080fbf--ENJQoXzR2LVC: Introduction (provision)
This means that paper has largely become obsolete in standardization, and page-oriented PDF files and single-page documents in natural language should be incrementally developed into machine-processable provisions that can be combined or fragmented as thematically required in the value creation process.
- bib.al.original-language: en
- bib.dp.publication-date: 2025-03-01
- ids.document: 99200
- ids.element: o1749224057163-introduction.nat
- ids.language-synoptic: o1749224057163-introduction.nat
- ids.tracing: hash-3302d0db3c41df393ba625d7263e81d9eefc45e415e8d9b82eb867ccd1fc154c
- obj.element-name: paragraph
- obj.language: en
- obj.modality: recommendation
- obj.normativity: normative
- obj.specobject-type: provision
- use.business-process: undefined
- use.business-sector: undefined
- use.interaction: undefined
- use.location: undefined
- use.product-category: undefined
- use.product-life-cycle: undefined
- use.project-phase: undefined
- use.purpose: undefined

### tr--6d400e6f-d82a-44a1-8922-1185ec080fbf--IEjT0bYwe6oS: Introduction (provision)
Challenges:
- Standard delivering organizations need to focus on the use of provisions and optimize the knowledge of authors and experts to meet the needs of standards users.
- Stakeholders of standard delivering organizations expect interoperable standards content regardless of the publisher or supplier. More specifically, solutions should not be proprietary for DIN, DKE, VDE, VDI or other CEN, CENELEC, IEC and ISO members, but should be compatible at the interfaces from the customer’s point of view (“from a single source”).
- bib.al.original-language: en
- bib.dp.publication-date: 2025-03-01
- ids.document: 99200
- ids.element: o1749224057163-introduction.nat
- ids.language-synoptic: o1749224057163-introduction.nat
- ids.tracing: hash-9964581b89a2c51b264a6c972346ad01814736ea2350c3f5762b20507a3f2bef
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

### tr--6d400e6f-d82a-44a1-8922-1185ec080fbf--owqn1OCZN61m: Introduction (provision)
To support the digital transformation, the German Institute for Standardization (DIN)^ ^1 and the German Commission for Electrical Engineering (DKE)^ ^2 have initiated the national Initiative for Digital Standards (IDiS) in Germany.
- bib.al.original-language: en
- bib.dp.publication-date: 2025-03-01
- ids.document: 99200
- ids.element: o1749224057163-introduction.nat
- ids.language-synoptic: o1749224057163-introduction.nat
- ids.tracing: hash-2e9f44102c050eb3f339e0acc5a04497d6ab3132c1fd39b38520e4e945f3a8d1
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-100000012-39f2b6eb5259498: Introduction (provision)
^1 de: DIN Deutsches Institut für Normung e. V.
- bib.al.original-language: en
- bib.dp.publication-date: 2025-03-01
- ids.document: 99200
- ids.element: o1749224057163-introduction.nat
- ids.language-synoptic: o1749224057163-introduction.nat
- ids.tracing: hash-252b0d15f3b51bc9063a466a8b027bcb0ccee6b489ab8915aa9dd9ddc80b7e63
- obj.element-name: footnote
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

#### prov-100000012-1e7feeb759eb42c: Introduction (provision)
^2 de: DKE Deutsche Kommission Elektrotechnik Elektronik Informationstechnik in DIN und VDE
- bib.al.original-language: en
- bib.dp.publication-date: 2025-03-01
- ids.document: 99200
- ids.element: o1749224057163-introduction.nat
- ids.language-synoptic: o1749224057163-introduction.nat
- ids.tracing: hash-fcf0d270e9272bdf697af4f19e0f1759f57601514166d722c468d850c8f568aa
- obj.element-name: footnote
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### tr--6d400e6f-d82a-44a1-8922-1185ec080fbf--2YJhtLOrBAkL: Introduction (provision)
The objectives for IDiS are:
- IDiS promotes the development and gradual establishment of the digital standard, to strengthen the competitiveness of the German economy and the future viability of our society in a digitally transformed world.
- IDiS is the leading independent think tank in Germany for the digital standard and its practical application.
- IDiS offers an exclusive expert community and knowledge platform for all aspects of the digital standard.
- bib.al.original-language: en
- bib.dp.publication-date: 2025-03-01
- ids.document: 99200
- ids.element: o1749224057163-introduction.nat
- ids.language-synoptic: o1749224057163-introduction.nat
- ids.tracing: hash-233867ddeded694eaada7862f2efc5ffeeb56366dff31f31151efd6f7f47bc81
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### tr--6d400e6f-d82a-44a1-8922-1185ec080fbf--nXbyuNPoPKm7: Introduction (provision)
This specification is based on the user stories determined by stakeholders of the IDiS project “ReqIF™ interpretation for public standards” (see Annex A) and the generic user stories according to the IDiS Whitepaper 2 [8].
- bib.al.original-language: en
- bib.dp.publication-date: 2025-03-01
- ids.document: 99200
- ids.element: o1749224057163-introduction.nat
- ids.language-synoptic: o1749224057163-introduction.nat
- ids.tracing: hash-7ee9eb0393c586da668af5c8c46b1165b3bb0c6a2c35e0e4ae394d564a31054b
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-cecca7a42e7f463
- cross-reference -> prov-100000012-402e6ac107ee49d

## prov-100000012-e4a89563f7e94c3: Scope (heading)
- bib.al.original-language: en
- bib.dp.publication-date: 2025-03-01
- ids.document: 99200
- ids.element: o1749224057168-sub-1
- ids.language-synoptic: o1749224057168-sub-1
- ids.tracing: hash-350bb3ee7b005be20fe4608f6183fee4d7b56a2f74faf6b655fcf7f7c6286d6f
- obj.clause-number: 1
- obj.element-name: heading
- obj.language: en
- obj.specobject-type: heading
- ChapterName: 1 Scope

### tr--6d400e6f-d82a-44a1-8922-1185ec080fbf--LGIXOzCQQ8ww: Scope (provision)
This document specifies the ReqIF™ interpretation for public standards, Release 1.3.
- bib.al.original-language: en
- bib.dp.publication-date: 2025-03-01
- ids.document: 99200
- ids.element: o1749224057168-sub-1
- ids.language-synoptic: o1749224057168-sub-1
- ids.tracing: hash-7915a5d5a5c553a33637dc24ba2e807ee31c8dfe9acf017e04bf3cf8890bfada
- obj.clause-number: 1
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### tr--6d400e6f-d82a-44a1-8922-1185ec080fbf--uCBoGoya90EV: Scope (provision)
This document specifies requirements on how to use ReqIF™ data types, attributes, attribute values and the semantical interpretation to achieve a unique interpretation of the same content by different stakeholders.
- bib.al.original-language: en
- bib.dp.publication-date: 2025-03-01
- ids.document: 99200
- ids.element: o1749224057168-sub-1
- ids.language-synoptic: o1749224057168-sub-1
- ids.tracing: hash-0a4e4f1fccc7073b4d70803e53924a2858acaf7912b724acc6c2ba1fff31e78e
- obj.clause-number: 1
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### tr--6d400e6f-d82a-44a1-8922-1185ec080fbf--ZNnRNWpNPDFT: Scope (provision)
This document covers the application of the ReqIF™ 1.2 format and specification.
- bib.al.original-language: en
- bib.dp.publication-date: 2025-03-01
- ids.document: 99200
- ids.element: o1749224057168-sub-1
- ids.language-synoptic: o1749224057168-sub-1
- ids.tracing: hash-57f4289b1d8b82dbb778886e88c48e87fdda3714acc0281e3a8bb7166b03eca9
- obj.clause-number: 1
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### tr--6d400e6f-d82a-44a1-8922-1185ec080fbf--JbnabGy30p1k: Scope (provision)
This document does not adopt or modify the ReqIF™ format and specification themselves.
- bib.al.original-language: en
- bib.dp.publication-date: 2025-03-01
- ids.document: 99200
- ids.element: o1749224057168-sub-1
- ids.language-synoptic: o1749224057168-sub-1
- ids.tracing: hash-249be2cd8513366720b4740067c8dcdf21d5f1a0bc94bd4b7e4636316cc421b5
- obj.clause-number: 1
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

## prov-100000012-a3da2132e4754a4: Normative references (heading)
- bib.al.original-language: en
- bib.dp.publication-date: 2025-03-01
- ids.document: 99200
- ids.element: o1749224057170-sub-2
- ids.language-synoptic: o1749224057170-sub-2
- ids.tracing: hash-429854a3d3b813f783e587b55b621a08e6da41ceabf387121309fee80e49b71f
- obj.clause-number: 2
- obj.element-name: heading
- obj.language: en
- obj.specobject-type: heading
- ChapterName: 2 Normative references

### tr--6d400e6f-d82a-44a1-8922-1185ec080fbf--UXOAxHdm7RKo: Normative references (provision)
The following documents are referred to in the text in such a way that some or all of their content constitutes requirements of this document.
- bib.al.original-language: en
- bib.dp.publication-date: 2025-03-01
- ids.document: 99200
- ids.element: o1749224057170-sub-2
- ids.language-synoptic: o1749224057170-sub-2
- ids.tracing: hash-9147d4e57c0f2f8cbea1bb8a6e1f4534e20c2fa0528f9b407fc271faed5aa19c
- obj.clause-number: 2
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### tr--6d400e6f-d82a-44a1-8922-1185ec080fbf--Df08keZg8gkq: Normative references (provision)
For dated references, only the edition cited applies.
- bib.al.original-language: en
- bib.dp.publication-date: 2025-03-01
- ids.document: 99200
- ids.element: o1749224057170-sub-2
- ids.language-synoptic: o1749224057170-sub-2
- ids.tracing: hash-6f2e39f151a8dd9917ab01e9af3cddc2803009a9a631436bdd07f38e0e2c3ca1
- obj.clause-number: 2
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### tr--6d400e6f-d82a-44a1-8922-1185ec080fbf--tzkrUdIgz8SX: Normative references (provision)
For undated references, the latest edition of the referenced document (including any amendments) applies.
- bib.al.original-language: en
- bib.dp.publication-date: 2025-03-01
- ids.document: 99200
- ids.element: o1749224057170-sub-2
- ids.language-synoptic: o1749224057170-sub-2
- ids.tracing: hash-33dfdc9e80b4e9a89e03fcd449a82a8ebdaf4e8fdae0f75ae5f5601874703711
- obj.clause-number: 2
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

### prov-100000012-dc89fc20f5524c5: Normative references (provision)
- DIN EN ISO 3166-1, Codes for the representation of names of countries and their subdivisions – Part 1: Country code
- DIN ISO 8601-1, Date and time – Representations for information interchange – Part 1: Basic rules
- DIN ISO 10241-1, Terminological entries in standards – Part 1: General requirements and examples of presentation
- ISO 639, Code for individual languages and language groups
- ISO/IEC 40314, Information technology – Mathematical Markup Language (MathML) Version 3.0; 2nd Edition
- ISO/IEC Directives, Part 2, Principles and rules for the structure and drafting of ISO and IEC documents
- Digital material to the ReqIF™ interpretation for public standards. DIN, DKE: Berlin, Offenbach. Internet: https://www.din-dke-spec-99200.de/
- ICS International Classification for Standards – edition 7. ISO: Genève, 2015
- ReqIF Implementation Guideline referring to OMG ReqIF1.2 – Version 1.10. prostep ivip: Darmstadt, 2024-01-26. Internet: https://www.prostep.org/
- Requirements Interchange Format (ReqIF) – Version 1.2. OMG, 2016-07-01. Internet: https://www.omg.org/spec/ReqIF/1.2/
- MathML Core. W3C Working Draft 27 November 2023. Internet: https://www.w3.org/TR/mathml-core/
- Metadata Field Specification. Metadata Consortium (AFNOR, BSI & DIN): Paris, London, Berlin, 2021-06-04. Internet: https://www.din-dke-spec-99200.de/
- XHTML™ 1.0 The Extensible HyperText Markup Language (Second Edition). W3C Recommendation 26 January 2000 revised 1 August 2002. Internet: https://www.w3.org/TR/xhtml1/
- XHTML™ Modularization 1.1 – Second Edition. W3C Recommendation 29 July 2010 superseded 27 March 2018. Internet: https://www.w3.org/TR/xhtml-modularization/
- bib.al.original-language: en
- bib.dp.publication-date: 2025-03-01
- ids.document: 99200
- ids.element: o1749224057170-sub-2
- ids.language-synoptic: o1749224057170-sub-2
- ids.tracing: hash-333467a5fe92def0ec523965a4c18bdbea566c8d6294b71fd5d8780cec90728a
- obj.clause-number: 2
- obj.element-name: list-of-documents
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

## prov-100000012-cb602b5c55cc408: Terms and definitions (heading)
- bib.al.original-language: en
- bib.dp.publication-date: 2025-03-01
- ids.document: 99200
- ids.element: o1749224057173-sub-3
- ids.language-synoptic: o1749224057173-sub-3
- ids.tracing: hash-45576d9476df03e23689a50e2da2d9182c8b449b2c14c4767e25f614e0c75cec
- obj.clause-number: 3
- obj.element-name: heading
- obj.language: en
- obj.specobject-type: heading
- ChapterName: 3 Terms and definitions

### tr--6d400e6f-d82a-44a1-8922-1185ec080fbf--1vATo9PA7Tbf: Terms and definitions (provision)
For the purposes of this document, the following terms and definitions apply.
- bib.al.original-language: en
- bib.dp.publication-date: 2025-03-01
- ids.document: 99200
- ids.element: o1749224057173-sub-3
- ids.language-synoptic: o1749224057173-sub-3
- ids.tracing: hash-b49520954e01d0e01341ec94c48b0d5c31c2af94c44877c4e5ac96d9fc89f018
- obj.clause-number: 3
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

### tr--6d400e6f-d82a-44a1-8922-1185ec080fbf--PoiCp5uSQ96e: Terms and definitions (provision)
DIN and DKE maintain terminological databases for use in standardization at the following addresses:
- DIN-TERMinologieportal: available at https://www.din.de/go/din-term
- DKE-IEV: available at https://www.dke.de/DKE-IEV
- bib.al.original-language: en
- bib.dp.publication-date: 2025-03-01
- ids.document: 99200
- ids.element: o1749224057173-sub-3
- ids.language-synoptic: o1749224057173-sub-3
- ids.tracing: hash-a1e974ffa31962c4e1c7907165b21e5bebae74de51d2d56bae27183638928883
- obj.clause-number: 3
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### tr--6d400e6f-d82a-44a1-8922-1185ec080fbf--eNm9uhZffn47: Terms and definitions (provision)
ISO and IEC maintain terminological databases for use in standardization at the following addresses:
- ISO Online browsing platform: available at https://www.iso.org/obp
- IEC Electropedia: available at https://www.electropedia.org/
- bib.al.original-language: en
- bib.dp.publication-date: 2025-03-01
- ids.document: 99200
- ids.element: o1749224057173-sub-3
- ids.language-synoptic: o1749224057173-sub-3
- ids.tracing: hash-241878b83e0991135978cf91b7c6d9011f03bfa8e80a2703861792db2a03779b
- obj.clause-number: 3
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-100000012-bacf383ecc94401: publicly available standard (provision)
3.1
publicly available standard
public standard
technical rule published by a recognized standardizing body or government organization
Note 1 to entry: For terminology on bodies and types of standards or regulations see ISO/IEC Guide 2.
Note 2 to entry: Although the title of this specification refers only to public standards explicitly, this specification can be agreed on for any type of publicly available technical rules as well as publicly available legislative regulations.
- bib.al.original-language: en
- bib.dp.publication-date: 2025-03-01
- ids.document: 99200
- ids.element: o1749224057175-sub-3.1
- ids.language-synoptic: o1749224057175-sub-3.1
- ids.tracing: hash-c669b3eb6a387f64f2cf0717572ef27cb1cbe4bd7edc99e091b72479b25a9858
- obj.clause-number: 3.1
- obj.element-name: concept
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-100000012-1c66c75156f04fd: requirements engineering (provision)
3.2
requirements engineering
RE
systematic process of defining, documenting, and maintaining requirements in the engineering design process
- bib.al.original-language: en
- bib.dp.publication-date: 2025-03-01
- ids.document: 99200
- ids.element: o1749224057177-sub-3.2
- ids.language-synoptic: o1749224057177-sub-3.2
- ids.tracing: hash-c01da03c57e9aaa6156756cb153e377c23c2299cdcee1310c7d5714f46b9f428
- obj.clause-number: 3.2
- obj.element-name: concept
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-100000012-36973eb801e34b5: requirements management (provision)
3.3
requirements management
RM
partial discipline of requirements engineering
- bib.al.original-language: en
- bib.dp.publication-date: 2025-03-01
- ids.document: 99200
- ids.element: o1749224057179-sub-3.3
- ids.language-synoptic: o1749224057179-sub-3.3
- ids.tracing: hash-bc267f6697c27d62302e142498f3132eedfdc498e31116365675330a14032f65
- obj.clause-number: 3.3
- obj.element-name: concept
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-100000012-bff15fb549b842d: requirements management system (provision)
3.4
requirements management system
RMS
content management system which is specialized to manage the content and metadata of requirements
- bib.al.original-language: en
- bib.dp.publication-date: 2025-03-01
- ids.document: 99200
- ids.element: o1749224057181-sub-3.4
- ids.language-synoptic: o1749224057181-sub-3.4
- ids.tracing: hash-4cab2440d0afd2eba14737774f2968453d7af271c3952195445c7ea2ff4bdf8e
- obj.clause-number: 3.4
- obj.element-name: concept
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-100000012-f8e63bd3aebf410: ReqIF™ (provision)
3.5
ReqIF™
Requirements Interchange Format™
file format for the exchange requirements, including its associated metadata, between software tools from different vendors
Note 1 to entry: ReqIF™ is a trademark of the Object Management Group, Inc.
Note 2 to entry: Requirements Interchange Format™ is a trademark of the Object Management Group, Inc.
- bib.al.original-language: en
- bib.dp.publication-date: 2025-03-01
- ids.document: 99200
- ids.element: o1749224057183-sub-3.5
- ids.language-synoptic: o1749224057183-sub-3.5
- ids.tracing: hash-84be8c6b39c04e43b8bddc38432c5ba3de04795712974fdb5bdb63cc1d18eb6f
- obj.clause-number: 3.5
- obj.element-name: concept
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-100000012-602e349c9b624e3: SMART Standards (provision)
3.6
SMART Standards
initiative for the digital transformation of standards content across the entire value creation chain with the objective of making the use of content in the context of Industry 4.0 gradually more efficient through increasing automation based on the utility model
Note 1 to entry: The acronym “SMART” (see IDiS Whitepaper 1) is capitalized and stands for:
- Standards;
- Machine;
- Applicable;
- Readable;
- Transferrable.
- bib.al.original-language: en
- bib.dp.publication-date: 2025-03-01
- ids.document: 99200
- ids.element: o1749224057185-sub-3.6
- ids.language-synoptic: o1749224057185-sub-3.6
- ids.tracing: hash-f17f1ff15461f410d8cb10beb03ee7c1bb4eb61e13643e09c68263c3801aae19
- obj.clause-number: 3.6
- obj.element-name: concept
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-100000012-f2b1b52639dd442: value creation chain (provision)
3.7
value creation chain
<SMART Standards> process relevant to the digital transformation of standard content with the value-creating process phases
Note 1 to entry: The value-creating process phases (see IDiS Whitepaper 1) are:
- content creation;
- content management;
- content delivery;
- content usage.
- bib.al.original-language: en
- bib.dp.publication-date: 2025-03-01
- ids.document: 99200
- ids.element: o1749224057187-sub-3.7
- ids.language-synoptic: o1749224057187-sub-3.7
- ids.tracing: hash-fc7f5fb3dfc3f43e37aa20f08abb7862ca24c3a01b54acaf731f0e24a84dfce8
- obj.clause-number: 3.7
- obj.element-name: concept
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-100000012-fdde53d24d22482: utility model (provision)
3.8
utility model
level model
<SMART Standards> milestones for the maturity level of the digital transformation, which is measured by the level achieved across the entire value creation chain
EXAMPLE: According to the utility model (see IDiS Whitepaper 1), requirements management matches level 3 of SMART Standards.
- bib.al.original-language: en
- bib.dp.publication-date: 2025-03-01
- ids.document: 99200
- ids.element: o1749224057189-sub-3.8
- ids.language-synoptic: o1749224057189-sub-3.8
- ids.tracing: hash-1b182e94d687db1ad222fa16149508dde0f1cf12c6682d3e3761c8b77979c28f
- obj.clause-number: 3.8
- obj.element-name: concept
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

## prov-100000012-d6eb80fd9ba6439: Challenges (heading)
- bib.al.original-language: en
- bib.dp.publication-date: 2025-03-01
- ids.document: 99200
- ids.element: o1749224057191-sub-4
- ids.language-synoptic: o1749224057191-sub-4
- ids.tracing: hash-05386ad4196ca72f3b66be647cf0c84fc91a9145f5b792340e57b30a6c5a3361
- obj.clause-number: 4
- obj.element-name: heading
- obj.language: en
- obj.specobject-type: heading
- ChapterName: 4 Challenges

### tr--6d400e6f-d82a-44a1-8922-1185ec080fbf--GPtFl0BjQ22g: Challenges (provision)
The challenges and potentials for improvement for the “ReqIF™ interpretation for public standards” are:
- ReqIF™ is a generic standard that is interpreted on a customer-specific basis;
- provisions: are determined not interoperable sentence-wise, paragraph-wise, division-wise, or intuitively;
- metadata: amount, naming, data types and values are defined on a not interoperable proprietary basis;
- SMART Standards (3.6): added values have not yet been harmonized;
- compatibility between different target software is limited;
- interoperability between companies is limited.
- bib.al.original-language: en
- bib.dp.publication-date: 2025-03-01
- ids.document: 99200
- ids.element: o1749224057191-sub-4
- ids.language-synoptic: o1749224057191-sub-4
- ids.tracing: hash-c007d2f9083b52f3292e1ca43fa8ec5fbb5a3165837b680eebc632e3106c5e14
- obj.clause-number: 4
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-602e349c9b624e3

## prov-100000012-dd4fb23ed7cb47e: Objectives (heading)
- bib.al.original-language: en
- bib.dp.publication-date: 2025-03-01
- ids.document: 99200
- ids.element: o1749224057193-sub-5
- ids.language-synoptic: o1749224057193-sub-5
- ids.tracing: hash-ff243908644ed6bbc339a57bf372c8cc5a150491e35b3b049def92ca2b2baddc
- obj.clause-number: 5
- obj.element-name: heading
- obj.language: en
- obj.specobject-type: heading
- ChapterName: 5 Objectives

### tr--6d400e6f-d82a-44a1-8922-1185ec080fbf--LcxoUCCIkLCD: Objectives (provision)
The objectives of the “ReqIF™ interpretation for public standards” are:
- harmonize ReqIF™ interpretation for public standards;
- improve interoperability between companies;
- integrate document metadata;
- integrate SMART metadata (3.6);
- cooperate with the committees relevant to ReqIF™ standardization;
- create basis for European and international harmonization.
- bib.al.original-language: en
- bib.dp.publication-date: 2025-03-01
- ids.document: 99200
- ids.element: o1749224057193-sub-5
- ids.language-synoptic: o1749224057193-sub-5
- ids.tracing: hash-e9d75b4bda600ddb1deffd9f7cfe8187ab111e286ccaac6f0c521ae13b33600e
- obj.clause-number: 5
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-602e349c9b624e3

## prov-100000012-b5fc4fa52c604d4: Target software (heading)
- bib.al.original-language: en
- bib.dp.publication-date: 2025-03-01
- ids.document: 99200
- ids.element: o1749224057195-sub-6
- ids.language-synoptic: o1749224057195-sub-6
- ids.tracing: hash-644056c69d2ec47f32e8ce084d2ce8f269e7e0f8cb1c2c1bb1703813fe8448b4
- obj.clause-number: 6
- obj.element-name: heading
- obj.language: en
- obj.specobject-type: heading
- ChapterName: 6 Target software

### tr--6d400e6f-d82a-44a1-8922-1185ec080fbf--YQAqc1OZyrnk: Target software (provision)
Since compatibility between different target software is limited, the suppliers may provide ReqIF™ file variants optimized for different target software for the time being.
- bib.al.original-language: en
- bib.dp.publication-date: 2025-03-01
- ids.document: 99200
- ids.element: o1749224057195-sub-6
- ids.language-synoptic: o1749224057195-sub-6
- ids.tracing: hash-bb12d9cf10f49c7e201252972d04f631d3a591db6f39e018a52f0a8edda33d24
- obj.clause-number: 6
- obj.element-name: paragraph
- obj.language: en
- obj.modality: permission
- obj.normativity: normative
- obj.specobject-type: provision
- use.business-process: undefined
- use.business-sector: undefined
- use.interaction: undefined
- use.location: undefined
- use.product-category: undefined
- use.product-life-cycle: undefined
- use.project-phase: undefined
- use.purpose: undefined

### tr--6d400e6f-d82a-44a1-8922-1185ec080fbf--3JghL36LsgVa: Target software (provision)
To achieve best interoperability, all stakeholders should improve on using only the preferred standard variant according to this specification and to the provided digital material (see Clause 11).
- bib.al.original-language: en
- bib.dp.publication-date: 2025-03-01
- ids.document: 99200
- ids.element: o1749224057195-sub-6
- ids.language-synoptic: o1749224057195-sub-6
- ids.tracing: hash-922591639d5b2c646aae8d00560d7e3edc2901d8f4b5528414b262ccb53c7c46
- obj.clause-number: 6
- obj.element-name: paragraph
- obj.language: en
- obj.modality: recommendation
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-cedd90735d8a4ba

### tr--6d400e6f-d82a-44a1-8922-1185ec080fbf--BH95oKaIoatQ: Target software (provision)
This specification is applicable for any target software which can process the version of ReqIF™ specified in Clause 1.
- bib.al.original-language: en
- bib.dp.publication-date: 2025-03-01
- ids.document: 99200
- ids.element: o1749224057195-sub-6
- ids.language-synoptic: o1749224057195-sub-6
- ids.tracing: hash-b839293143b8eccdd85b82c511ee96c2eacac5387b2de94718035e36e80321f3
- obj.clause-number: 6
- obj.element-name: paragraph
- obj.language: en
- obj.modality: permission
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-e4a89563f7e94c3

### tr--6d400e6f-d82a-44a1-8922-1185ec080fbf--Oxv8RjQAM6n1: Target software (provision)
This specification has been implemented and so-far tested with the target software of following vendors:
- IBM DOORS Classic^ ^3 ;
- Jama Connect + Data Exchange^3;
- PTC Codebeamer^3;
- PTC Windchill RV&S + Requirements Connector^3;
- Siemens Polarion^3.
- bib.al.original-language: en
- bib.dp.publication-date: 2025-03-01
- ids.document: 99200
- ids.element: o1749224057195-sub-6
- ids.language-synoptic: o1749224057195-sub-6
- ids.tracing: hash-41c329ed4f000d8f2a8d7439dcbeb43cde3038792527ce9766bd922a63bca135
- obj.clause-number: 6
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-100000012-58618cd84be8477: Target software (provision)
^3 This is the trade name of a product supplied by the vendor mentioned initially. This information is given for the convenience of users of this document and does not constitute an endorsement by DIN or DKE of the product named. Equivalent products may be used if they can be shown to lead to the same results.
- bib.al.original-language: en
- bib.dp.publication-date: 2025-03-01
- ids.document: 99200
- ids.element: o1749224057195-sub-6
- ids.language-synoptic: o1749224057195-sub-6
- ids.tracing: hash-c0ad9ca485f17a62f482190eb24be037a85c29ec2d0cd906f40b02ca7e6604a6
- obj.clause-number: 6
- obj.element-name: footnote
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### tr--6d400e6f-d82a-44a1-8922-1185ec080fbf--Aiegu1Ulo2DD: Target software (provision)
This specification is not limited to the target software of any vendors.
- bib.al.original-language: en
- bib.dp.publication-date: 2025-03-01
- ids.document: 99200
- ids.element: o1749224057195-sub-6
- ids.language-synoptic: o1749224057195-sub-6
- ids.tracing: hash-c27c824c17782dcc8b32158c528d935dc64cc9dbf99d69d4bcd09fd9b3047e1d
- obj.clause-number: 6
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

## prov-100000012-71b3229623d6417: Application best-practice (heading)
- bib.al.original-language: en
- bib.dp.publication-date: 2025-03-01
- ids.document: 99200
- ids.element: o1749224057198-sub-7
- ids.language-synoptic: o1749224057198-sub-7
- ids.tracing: hash-193126026cba9e4f4d435b52abcf7a05ae414ba44c8f95a684257daa6e369e59
- obj.clause-number: 7
- obj.element-name: heading
- obj.language: en
- obj.specobject-type: heading
- ChapterName: 7 Application best-practice

### prov-100000012-696f8f66ded24ed: Internal standard versus interchange format (heading)
- bib.al.original-language: en
- bib.dp.publication-date: 2025-03-01
- ids.document: 99200
- ids.element: o1749224057200-sub-7.1
- ids.language-synoptic: o1749224057200-sub-7.1
- ids.tracing: hash-792153a4341f0e0ab66b4c2d8ec2d65259109c89e58a5bdc1097faca2ed1b462
- obj.clause-number: 7.1
- obj.element-name: heading
- obj.language: en
- obj.specobject-type: heading
- ChapterName: 7.1 Internal standard versus interchange format

#### tr--6d400e6f-d82a-44a1-8922-1185ec080fbf--5zKMFXzbq067: Internal standard versus interchange format (provision)
Users have the following options to deal with this specification, depending on the preconditions:
- If the users’ company has no internal standard interpretation for their RMS and this specification matches the user’s requirements, the users should adopt and implement this specification as internal standard to achieve the optimal efficiency and interoperability with other companies.
- If the users’ company has already an internal standard interpretation for their RMS or this specification does not match the user’s requirements, the users should implement this specification for the import and export processes to achieve a sufficient level of interoperability with other companies.
- bib.al.original-language: en
- bib.dp.publication-date: 2025-03-01
- ids.document: 99200
- ids.element: o1749224057200-sub-7.1
- ids.language-synoptic: o1749224057200-sub-7.1
- ids.tracing: hash-fd626b7c2008645784693e75d56259591c482845f810f2f3376b6203ec29f518
- obj.clause-number: 7.1
- obj.element-name: paragraph
- obj.language: en
- obj.modality: recommendation
- obj.normativity: normative
- obj.specobject-type: provision
- use.business-process: undefined
- use.business-sector: undefined
- use.interaction: undefined
- use.location: undefined
- use.product-category: undefined
- use.product-life-cycle: undefined
- use.project-phase: undefined
- use.purpose: undefined

#### prov-100000012-bfbb1b03d5f7495: Internal standard versus interchange format, Note (provision)
NOTE:
Figure 1 illustrates that situation where communication under n stakeholders implies that each stakeholder maintains n − 1 individual import mapping variants, whereas Figure 2 illustrates a situation where communication under n stakeholders via an exchange standard can be achieved with only one import mapping if this specification has been agreed on.
- bib.al.original-language: en
- bib.dp.publication-date: 2025-03-01
- ids.document: 99200
- ids.element: o1749224057200-sub-7.1
- ids.language-synoptic: o1749224057200-sub-7.1
- ids.tracing: hash-ee16b9a9d93acdfc2aca088133f1a2ad93e1e1f239ea23ac2a1d7618ab1a623e
- obj.clause-number: 7.1
- obj.element-name: note
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
- cross-reference -> prov-100000012-cf3c4772f4c8484
- cross-reference -> prov-100000012-59f6a50d79744fb

#### prov-100000012-cf3c4772f4c8484: Internal standard versus interchange format (provision)
Figure 1 — n to n communication
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- bib.al.original-language: en
- bib.dp.publication-date: 2025-03-01
- ids.document: 99200
- ids.element: o1749224057200-sub-7.1
- ids.language-synoptic: o1749224057200-sub-7.1
- ids.tracing: hash-c83d5a6c2e14aa63a899b33104efc877c00a98495e001e27e41eb52dbe203ad6
- obj.clause-number: 7.1
- obj.element-name: figure
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-100000012-59f6a50d79744fb: Internal standard versus interchange format (provision)
Figure 2 — n via 1 communication
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- bib.al.original-language: en
- bib.dp.publication-date: 2025-03-01
- ids.document: 99200
- ids.element: o1749224057200-sub-7.1
- ids.language-synoptic: o1749224057200-sub-7.1
- ids.tracing: hash-b437fca165a2f03eec47c3d62facc3d0ed82f53cbfc3a9ed5072ef1628c361fc
- obj.clause-number: 7.1
- obj.element-name: figure
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-100000012-fbf4c4611b6d45c: Configuration issues for target software (heading)
- bib.al.original-language: en
- bib.dp.publication-date: 2025-03-01
- ids.document: 99200
- ids.element: o1749224057202-sub-7.2
- ids.language-synoptic: o1749224057202-sub-7.2
- ids.tracing: hash-8a4e204455d538197076a7ebb46ce48431f04b121e3f85156ac8d1b19c78839a
- obj.clause-number: 7.2
- obj.element-name: heading
- obj.language: en
- obj.specobject-type: heading
- ChapterName: 7.2 Configuration issues for target software

#### tr--6d400e6f-d82a-44a1-8922-1185ec080fbf--JFuzEPMwbjg5: Configuration issues for target software (provision)
If ReqIF™ files according to this specification are imported, a common behavior of target software is to sort the attributes in alphabetical instead of the logical order according to the data model (see 8.2).
- bib.al.original-language: en
- bib.dp.publication-date: 2025-03-01
- ids.document: 99200
- ids.element: o1749224057202-sub-7.2
- ids.language-synoptic: o1749224057202-sub-7.2
- ids.tracing: hash-c8bc569c9b0fd4fa9038a0f5083a7dedc16b2b182b14f68b6594d52f4bad6098
- obj.clause-number: 7.2
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-252f89746a5e4d1

#### tr--6d400e6f-d82a-44a1-8922-1185ec080fbf--YeBTuNo0uSrt: Configuration issues for target software (provision)
If the logical order according to the data model (see 8.2) is preferred, the order of attributes shall be configured for the target software.
- bib.al.original-language: en
- bib.dp.publication-date: 2025-03-01
- ids.document: 99200
- ids.element: o1749224057202-sub-7.2
- ids.language-synoptic: o1749224057202-sub-7.2
- ids.tracing: hash-e4f503fe73050410b3cc2d21da9e301d0ad942a5b1b7dde53753acd9ac5ce92a
- obj.clause-number: 7.2
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-252f89746a5e4d1

#### tr--6d400e6f-d82a-44a1-8922-1185ec080fbf--12UG7egqDLpr: Configuration issues for target software (provision)
If the logical order according to the data model (see 8.2) is preferred, the users should investigate for their target software whether:
- digital material (see 7.3) for the import and configuration is available, i. e. scripts or import templates; or
- support for the configuration can be obtained if demanded.
- bib.al.original-language: en
- bib.dp.publication-date: 2025-03-01
- ids.document: 99200
- ids.element: o1749224057202-sub-7.2
- ids.language-synoptic: o1749224057202-sub-7.2
- ids.tracing: hash-5115e64a0357ec92046cde4c2cb6b60c0f33aed281d7d304898788251d46025f
- obj.clause-number: 7.2
- obj.element-name: paragraph
- obj.language: en
- obj.modality: recommendation
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-252f89746a5e4d1
- cross-reference -> prov-100000012-5a64252d1a58418

### prov-100000012-5a64252d1a58418: Digital material for the import and export process (heading)
- bib.al.original-language: en
- bib.dp.publication-date: 2025-03-01
- ids.document: 99200
- ids.element: o1749224057204-sub-7.3
- ids.language-synoptic: o1749224057204-sub-7.3
- ids.tracing: hash-6a12234240873f6f69cc7f4c8b2454d7bb34103001f2f307715fd683447aff91
- obj.clause-number: 7.3
- obj.element-name: heading
- obj.language: en
- obj.specobject-type: heading
- ChapterName: 7.3 Digital material for the import and export process

#### tr--6d400e6f-d82a-44a1-8922-1185ec080fbf--LgQUrbbBucAg: Digital material for the import and export process (provision)
Digital material to the ReqIF™ interpretation for public standards is provided on the official web page to support the import process, management process and export process in the target software (see Clause 11):
- benchmarking documents for interoperability tests;
- example documents to support understanding and implementing this specification;
- tables to the data model as MS® Excel®^ ^3 file;
- utilities for the import and export processes (templates);
- Schematron for the validation against the data model of this specification to improve interoperability.
- bib.al.original-language: en
- bib.dp.publication-date: 2025-03-01
- ids.document: 99200
- ids.element: o1749224057204-sub-7.3
- ids.language-synoptic: o1749224057204-sub-7.3
- ids.tracing: hash-9f802877bb8cb1296cc4b33a966ff6c700cec8bb6e9de16a4be67f98b57f72d7
- obj.clause-number: 7.3
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-cedd90735d8a4ba

#### tr--6d400e6f-d82a-44a1-8922-1185ec080fbf--Ctc7kcLKHe0y: Digital material for the import and export process (provision)
The users should investigate whether digital material is available for their target software.
- bib.al.original-language: en
- bib.dp.publication-date: 2025-03-01
- ids.document: 99200
- ids.element: o1749224057204-sub-7.3
- ids.language-synoptic: o1749224057204-sub-7.3
- ids.tracing: hash-7cc8fa2c84656af179380088d8846bd1271c0d0ee1d0c00451f0e2c5af10204a
- obj.clause-number: 7.3
- obj.element-name: paragraph
- obj.language: en
- obj.modality: recommendation
- obj.normativity: normative
- obj.specobject-type: provision
- use.business-process: undefined
- use.business-sector: undefined
- use.interaction: undefined
- use.location: undefined
- use.product-category: undefined
- use.product-life-cycle: undefined
- use.project-phase: undefined
- use.purpose: undefined

#### tr--6d400e6f-d82a-44a1-8922-1185ec080fbf--1xFW1O5X1hSR: Digital material for the import and export process (provision)
Since the digital material is subject of the continuous improvement process, the users should frequently check whether updates of digital material relevant for them is available.
- bib.al.original-language: en
- bib.dp.publication-date: 2025-03-01
- ids.document: 99200
- ids.element: o1749224057204-sub-7.3
- ids.language-synoptic: o1749224057204-sub-7.3
- ids.tracing: hash-6015f1633fc3a6d4f06624db5b9512479bfd65214207ac53b14c3caf91a582aa
- obj.clause-number: 7.3
- obj.element-name: paragraph
- obj.language: en
- obj.modality: recommendation
- obj.normativity: normative
- obj.specobject-type: provision
- use.business-process: undefined
- use.business-sector: undefined
- use.interaction: undefined
- use.location: undefined
- use.product-category: undefined
- use.product-life-cycle: undefined
- use.project-phase: undefined
- use.purpose: undefined

### prov-100000012-1727ad28f4d5461: Conforming application (heading)
- bib.al.original-language: en
- bib.dp.publication-date: 2025-03-01
- ids.document: 99200
- ids.element: o1749224057206-sub-7.4
- ids.language-synoptic: o1749224057206-sub-7.4
- ids.tracing: hash-356ec37b23aa72ba533372fabcc99d79b48d8b9c320bac6d70245aaf65f401bc
- obj.clause-number: 7.4
- obj.element-name: heading
- obj.language: en
- obj.specobject-type: heading
- ChapterName: 7.4 Conforming application

#### tr--6d400e6f-d82a-44a1-8922-1185ec080fbf--mPpUAkOC8UcX: Conforming application (provision)
Requirements for a conforming application of this specification are:
- The data model for this interpretation shall be implemented as specified in Clause 8.
- The attributes shall be implemented as specified in 8.2.
- The attributes for the document shall be implemented as specified in 8.1.2.
- The list of values for attributes shall be implemented as specified in 8.3.
- The declarations and definitions shall be implemented as specified in 8.4, based on the conventions in 8.5.
- The semantic interpretation shall be according to Clause 9.
- The presentation shall be according to Clause 10.
- The ReqIF™ file shall conform to the OMG ReqIF™ 1.2 specification.
- The ReqIF™ file shall validate against the ReqIF™ 1.2 XML Schema Definition.
- The ReqIF™ file shall conform to the actual prostep ReqIF™ 1.2 guideline.
- The ReqIF™ file shall validate against the Schematron for this specification without errors (see 11.5).
- After performing a round-trip process, the DIN DKE benchmarking file shall be without change or loss of attributes, values and without issues relevant for the interpretation of provisions (see 11.1).
- bib.al.original-language: en
- bib.dp.publication-date: 2025-03-01
- ids.document: 99200
- ids.element: o1749224057206-sub-7.4
- ids.language-synoptic: o1749224057206-sub-7.4
- ids.tracing: hash-f438e227ed4e84d39893e4ef43e07829956728f7c428ba36b2ffb571f161ee97
- obj.clause-number: 7.4
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-4727c816591a468
- cross-reference -> prov-100000012-252f89746a5e4d1
- cross-reference -> prov-100000012-58f2305abf05458
- cross-reference -> prov-100000012-62b877911c1c4ff
- cross-reference -> prov-100000012-e0c5df8513054b8
- cross-reference -> prov-100000012-5397288d2c3b4f7
- cross-reference -> prov-100000012-a745655795d147d
- cross-reference -> prov-100000012-5934fd9e743b4e2
- cross-reference -> prov-100000012-518d82a669ff4f2
- cross-reference -> prov-100000012-17d729caeefe4e1

## prov-100000012-4727c816591a468: Data model (heading)
- bib.al.original-language: en
- bib.dp.publication-date: 2025-03-01
- ids.document: 99200
- ids.element: o1749224057209-sub-8
- ids.language-synoptic: o1749224057209-sub-8
- ids.tracing: hash-8c6d33d705faa22280015abd7c5db01923c78b9212e8090f5055e3915bb42e0a
- obj.clause-number: 8
- obj.element-name: heading
- obj.language: en
- obj.specobject-type: heading
- ChapterName: 8 Data model

### prov-100000012-54694154d33a48b: Structural overview (heading)
- bib.al.original-language: en
- bib.dp.publication-date: 2025-03-01
- ids.document: 99200
- ids.element: o1749224057212-sub-8.1
- ids.language-synoptic: o1749224057212-sub-8.1
- ids.tracing: hash-5cb4e23ce0f75c1d6afb1540cdf9f48e3a645154a853b22055150606a89284b5
- obj.clause-number: 8.1
- obj.element-name: heading
- obj.language: en
- obj.specobject-type: heading
- ChapterName: 8.1 Structural overview

#### prov-100000012-c192595f166b407: Information on the provision (SpecObject) (heading)
- bib.al.original-language: en
- bib.dp.publication-date: 2025-03-01
- ids.document: 99200
- ids.element: o1749224057215-sub-8.1.1
- ids.language-synoptic: o1749224057215-sub-8.1.1
- ids.tracing: hash-4a63a780e841d4f924df6bf86eb447877b2c8cd70ab08a42397a346013a6dedb
- obj.clause-number: 8.1.1
- obj.element-name: heading
- obj.language: en
- obj.specobject-type: heading
- ChapterName: 8.1.1 Information on the provision (SpecObject)

##### prov-100000012-59a4bd855f704ef: Content attributes on the provision (SpecObject) (heading)
- bib.al.original-language: en
- bib.dp.publication-date: 2025-03-01
- ids.document: 99200
- ids.element: o1749224057217-sub-8.1.1.1
- ids.language-synoptic: o1749224057217-sub-8.1.1.1
- ids.tracing: hash-5051100b864d083a6d5769c859a2e9d420849c630a48f88a55e9a28ed3ee7836
- obj.clause-number: 8.1.1.1
- obj.element-name: heading
- obj.language: en
- obj.specobject-type: heading
- ChapterName: 8.1.1.1 Content attributes on the provision (SpecObject)

###### tr--6d400e6f-d82a-44a1-8922-1185ec080fbf--KIogqqUQbvAr: Content attributes on the provision (SpecObject) (provision)
The content attributes (see 8.2.1.1) contain the text content of the provision from the public standard.
- bib.al.original-language: en
- bib.dp.publication-date: 2025-03-01
- ids.document: 99200
- ids.element: o1749224057217-sub-8.1.1.1
- ids.language-synoptic: o1749224057217-sub-8.1.1.1
- ids.tracing: hash-37ef6f3ebb71d4cabbc4ba4151975de52893d5603123595981e5bd84c39f3b08
- obj.clause-number: 8.1.1.1
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-b3b3b3964862457

###### tr--6d400e6f-d82a-44a1-8922-1185ec080fbf--KfbJAq9pUrU0: Content attributes on the provision (SpecObject) (provision)
The content attributes shall be provided by the supplier of the ReqIF™ file for the public standard (see 9.6).
- bib.al.original-language: en
- bib.dp.publication-date: 2025-03-01
- ids.document: 99200
- ids.element: o1749224057217-sub-8.1.1.1
- ids.language-synoptic: o1749224057217-sub-8.1.1.1
- ids.tracing: hash-f2a501b71f4737ba9e7b4f2d0c6ce36e0051dc0ee85e7b0cc4cf1de30f17204d
- obj.clause-number: 8.1.1.1
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-ffcbbe0b3d36446

###### tr--6d400e6f-d82a-44a1-8922-1185ec080fbf--AF7feXLAa59n: Content attributes on the provision (SpecObject) (provision)
The users can use the content attributes to filter, search and manage provisions.
- bib.al.original-language: en
- bib.dp.publication-date: 2025-03-01
- ids.document: 99200
- ids.element: o1749224057217-sub-8.1.1.1
- ids.language-synoptic: o1749224057217-sub-8.1.1.1
- ids.tracing: hash-d4bea75b876217a603df0f5037260a0fe085bee7b5db3a7a886e109d2368f511
- obj.clause-number: 8.1.1.1
- obj.element-name: paragraph
- obj.language: en
- obj.modality: permission
- obj.normativity: normative
- obj.specobject-type: provision
- obj.transformation-issues: Possibly wrong modal verb
- use.business-process: undefined
- use.business-sector: undefined
- use.interaction: undefined
- use.location: undefined
- use.product-category: undefined
- use.product-life-cycle: undefined
- use.project-phase: undefined
- use.purpose: undefined

###### tr--6d400e6f-d82a-44a1-8922-1185ec080fbf--92QAUtOXq7tr: Content attributes on the provision (SpecObject) (provision)
The content attributes are the first block of the data model to facilitate the most frequent accesses.
- bib.al.original-language: en
- bib.dp.publication-date: 2025-03-01
- ids.document: 99200
- ids.element: o1749224057217-sub-8.1.1.1
- ids.language-synoptic: o1749224057217-sub-8.1.1.1
- ids.tracing: hash-123659e23745cd217c65350ceb6e50ba9aba03e13a7933cb02c66317762d315e
- obj.clause-number: 8.1.1.1
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

###### prov-100000012-ce46278acc7a4eb: Content attributes on the provision (SpecObject), Note (provision)
NOTE:
Figure 3 illustrates the information blocks of the data model (see 8.2).
- bib.al.original-language: en
- bib.dp.publication-date: 2025-03-01
- ids.document: 99200
- ids.element: o1749224057217-sub-8.1.1.1
- ids.language-synoptic: o1749224057217-sub-8.1.1.1
- ids.tracing: hash-1f4354c0ab34118b333c6fa0e5eeeef5eb946d7041a009aa60bc8f5abd6978ae
- obj.clause-number: 8.1.1.1
- obj.element-name: note
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
- cross-reference -> prov-100000012-56441a58585b4c5
- cross-reference -> prov-100000012-252f89746a5e4d1

###### prov-100000012-56441a58585b4c5: Content attributes on the provision (SpecObject) (provision)
Figure 3 — Data model to the ReqIF™ interpretation for public standards
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- bib.al.original-language: en
- bib.dp.publication-date: 2025-03-01
- ids.document: 99200
- ids.element: o1749224057217-sub-8.1.1.1
- ids.language-synoptic: o1749224057217-sub-8.1.1.1
- ids.tracing: hash-55f0473c303c66d8b9520563a5dbab61308dc9b36f43080150b500a34a6f8856
- obj.clause-number: 8.1.1.1
- obj.element-name: figure
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-ce093609d6a8459: Object attributes on the provision (SpecObject) (heading)
- bib.al.original-language: en
- bib.dp.publication-date: 2025-03-01
- ids.document: 99200
- ids.element: o1749224057219-sub-8.1.1.2
- ids.language-synoptic: o1749224057219-sub-8.1.1.2
- ids.tracing: hash-e4e3e10028647dc212cc33e67f3e20c17c1b58917f57b9304a38ce3dc57d3348
- obj.clause-number: 8.1.1.2
- obj.element-name: heading
- obj.language: en
- obj.specobject-type: heading
- ChapterName: 8.1.1.2 Object attributes on the provision (SpecObject)

###### tr--6d400e6f-d82a-44a1-8922-1185ec080fbf--4IqLj4O96vRp: Object attributes on the provision (SpecObject) (provision)
The object attributes (see 8.2.1.2) contain the description for the characteristics of the provision content, such as the number and heading of its context, its language, and its modality.
- bib.al.original-language: en
- bib.dp.publication-date: 2025-03-01
- ids.document: 99200
- ids.element: o1749224057219-sub-8.1.1.2
- ids.language-synoptic: o1749224057219-sub-8.1.1.2
- ids.tracing: hash-ea08d43d79aa19b0269b49d39ed0552c242df433d0fa52e5916c9e689c913b36
- obj.clause-number: 8.1.1.2
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-2f90c5903f8d49c

###### tr--6d400e6f-d82a-44a1-8922-1185ec080fbf--q2ppvGnlDees: Object attributes on the provision (SpecObject) (provision)
The object attributes should be provided by the supplier of the ReqIF™ file for a public standard (see 9.7).
- bib.al.original-language: en
- bib.dp.publication-date: 2025-03-01
- ids.document: 99200
- ids.element: o1749224057219-sub-8.1.1.2
- ids.language-synoptic: o1749224057219-sub-8.1.1.2
- ids.tracing: hash-bc372d60de57a25f4f25b505ce8aef17eedea60dccaee7337d31e99a7e64b3f3
- obj.clause-number: 8.1.1.2
- obj.element-name: paragraph
- obj.language: en
- obj.modality: recommendation
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-c7e10059bbec4ec

###### tr--6d400e6f-d82a-44a1-8922-1185ec080fbf--KTn7PiuXbWUx: Object attributes on the provision (SpecObject) (provision)
The users can use the object attributes to filter, search and manage provisions.
- bib.al.original-language: en
- bib.dp.publication-date: 2025-03-01
- ids.document: 99200
- ids.element: o1749224057219-sub-8.1.1.2
- ids.language-synoptic: o1749224057219-sub-8.1.1.2
- ids.tracing: hash-3beb7c817f547358efb0277cbcf55ae0b356b6626ee525bd1e875e08faa335f7
- obj.clause-number: 8.1.1.2
- obj.element-name: paragraph
- obj.language: en
- obj.modality: permission
- obj.normativity: normative
- obj.specobject-type: provision
- obj.transformation-issues: Possibly wrong modal verb
- use.business-process: undefined
- use.business-sector: undefined
- use.interaction: undefined
- use.location: undefined
- use.product-category: undefined
- use.product-life-cycle: undefined
- use.project-phase: undefined
- use.purpose: undefined

###### tr--6d400e6f-d82a-44a1-8922-1185ec080fbf--9DJc4UtnTGwa: Object attributes on the provision (SpecObject) (provision)
The object attributes are the second block of the data model to facilitate the second-most frequent accesses.
- bib.al.original-language: en
- bib.dp.publication-date: 2025-03-01
- ids.document: 99200
- ids.element: o1749224057219-sub-8.1.1.2
- ids.language-synoptic: o1749224057219-sub-8.1.1.2
- ids.tracing: hash-e208bee4b486fba8ed7d4046f3bdfb50c928d95b343830b9b777c784ceaab30c
- obj.clause-number: 8.1.1.2
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

###### prov-100000012-2a50a29d75f0447: Object attributes on the provision (SpecObject), Note (provision)
NOTE:
The object attributes are based on the “SMART standard model” (see 3.6).
- bib.al.original-language: en
- bib.dp.publication-date: 2025-03-01
- ids.document: 99200
- ids.element: o1749224057219-sub-8.1.1.2
- ids.language-synoptic: o1749224057219-sub-8.1.1.2
- ids.tracing: hash-b3ef300ea28360b3a3aa98e2cc3f01a64da093675156ee3a0cea5e7e4fbfbd2c
- obj.clause-number: 8.1.1.2
- obj.element-name: note
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
- cross-reference -> prov-100000012-602e349c9b624e3

##### prov-100000012-c76e6a97910b435: Use attributes for intra-company management of the provision (SpecObject) (heading)
- bib.al.original-language: en
- bib.dp.publication-date: 2025-03-01
- ids.document: 99200
- ids.element: o1749224057221-sub-8.1.1.3
- ids.language-synoptic: o1749224057221-sub-8.1.1.3
- ids.tracing: hash-66a9aec58442609afa360b332d703ef0f827f3ec373d4fd9596e9e16308a72c0
- obj.clause-number: 8.1.1.3
- obj.element-name: heading
- obj.language: en
- obj.specobject-type: heading
- ChapterName: 8.1.1.3 Use attributes for intra-company management of the provision (SpecObject)

###### tr--6d400e6f-d82a-44a1-8922-1185ec080fbf--qlWi2QJScdT3: Use attributes for intra-company management of the provision (SpecObject) (provision)
The use attributes (see 8.2.1.3) are an additional set of standardized metadata to classify provisions, e. g., within the business process, product life cycle or project phase.
- bib.al.original-language: en
- bib.dp.publication-date: 2025-03-01
- ids.document: 99200
- ids.element: o1749224057221-sub-8.1.1.3
- ids.language-synoptic: o1749224057221-sub-8.1.1.3
- ids.tracing: hash-2f6881b393457abba31f643a934ce70e0f598842e7a587a653d98dca204eca3b
- obj.clause-number: 8.1.1.3
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-84c18c91f471404

###### tr--6d400e6f-d82a-44a1-8922-1185ec080fbf--Q4n2MblgDdbS: Use attributes for intra-company management of the provision (SpecObject) (provision)
Since use attributes can be assigned by end-users only, the use attributes cannot be provided by the supplier of the ReqIF™ file for a public standard (see 9.8).
- bib.al.original-language: en
- bib.dp.publication-date: 2025-03-01
- ids.document: 99200
- ids.element: o1749224057221-sub-8.1.1.3
- ids.language-synoptic: o1749224057221-sub-8.1.1.3
- ids.tracing: hash-3652cb2b6d7eb9d06471dab5677da6ebba88af15666275e362f9417226055280
- obj.clause-number: 8.1.1.3
- obj.element-name: paragraph
- obj.language: en
- obj.modality: permission
- obj.normativity: normative
- obj.specobject-type: provision
- obj.transformation-issues: Possibly wrong modal verb
- use.business-process: undefined
- use.business-sector: undefined
- use.interaction: undefined
- use.location: undefined
- use.product-category: undefined
- use.product-life-cycle: undefined
- use.project-phase: undefined
- use.purpose: undefined
- cross-reference -> prov-100000012-c256799558ec4cb

###### tr--6d400e6f-d82a-44a1-8922-1185ec080fbf--IC6LYQZcigPG: Use attributes for intra-company management of the provision (SpecObject) (provision)
The users can use the use attributes to filter, search and manage provisions.
- bib.al.original-language: en
- bib.dp.publication-date: 2025-03-01
- ids.document: 99200
- ids.element: o1749224057221-sub-8.1.1.3
- ids.language-synoptic: o1749224057221-sub-8.1.1.3
- ids.tracing: hash-dc9e0bf1bf9d984eb9d34627be53865e56d4b90f9ee92f7e9036d834b8937c53
- obj.clause-number: 8.1.1.3
- obj.element-name: paragraph
- obj.language: en
- obj.modality: permission
- obj.normativity: normative
- obj.specobject-type: provision
- obj.transformation-issues: Possibly wrong modal verb
- use.business-process: undefined
- use.business-sector: undefined
- use.interaction: undefined
- use.location: undefined
- use.product-category: undefined
- use.product-life-cycle: undefined
- use.project-phase: undefined
- use.purpose: undefined

###### tr--6d400e6f-d82a-44a1-8922-1185ec080fbf--d7a5Ek76pqL6: Use attributes for intra-company management of the provision (SpecObject) (provision)
The use attributes are the third block of the data model to facilitate the third-most frequent accesses.
- bib.al.original-language: en
- bib.dp.publication-date: 2025-03-01
- ids.document: 99200
- ids.element: o1749224057221-sub-8.1.1.3
- ids.language-synoptic: o1749224057221-sub-8.1.1.3
- ids.tracing: hash-251e46ed4be9bf9bcc384de104a0293538573564ce828de6a1afaf48cf586851
- obj.clause-number: 8.1.1.3
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

###### prov-100000012-24775139d225498: Use attributes for intra-company management of the provision (SpecObject), Note (provision)
NOTE:
The use attributes are based on the “SMART use model” (see 3.6).
- bib.al.original-language: en
- bib.dp.publication-date: 2025-03-01
- ids.document: 99200
- ids.element: o1749224057221-sub-8.1.1.3
- ids.language-synoptic: o1749224057221-sub-8.1.1.3
- ids.tracing: hash-beb6af51ae476ee613ef1774eb5a863ec0e02f7e32e4a9749f54ff9f4abb02d3
- obj.clause-number: 8.1.1.3
- obj.element-name: note
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
- cross-reference -> prov-100000012-602e349c9b624e3

##### prov-100000012-b8b438a9fc0442b: Bibliographic document metadata (Perinorm 1.000) (heading)
- bib.al.original-language: en
- bib.dp.publication-date: 2025-03-01
- ids.document: 99200
- ids.element: o1749224057223-sub-8.1.1.4
- ids.language-synoptic: o1749224057223-sub-8.1.1.4
- ids.tracing: hash-0ed2c2d62b18641ebb28ec1310b83a57f3f1910530adb1b265bbce71f462b1ae
- obj.clause-number: 8.1.1.4
- obj.element-name: heading
- obj.language: en
- obj.specobject-type: heading
- ChapterName: 8.1.1.4 Bibliographic document metadata (Perinorm 1.000)

###### tr--6d400e6f-d82a-44a1-8922-1185ec080fbf--QngnGcROuOqU: Bibliographic document metadata (Perinorm 1.000) (provision)
The bibliographic document metadata (see 8.2.1.4) contain a selection of fields from the set of metadata according to the Metadata Field Specification standardized by the Metadata Consortium of AFNOR, BSI and DIN.
- bib.al.original-language: en
- bib.dp.publication-date: 2025-03-01
- ids.document: 99200
- ids.element: o1749224057223-sub-8.1.1.4
- ids.language-synoptic: o1749224057223-sub-8.1.1.4
- ids.tracing: hash-a783c2583f88f519d7d90d226138e44781dea93412baf18264c2904b79308ee7
- obj.clause-number: 8.1.1.4
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-ac76d054ec4c4b2

###### tr--6d400e6f-d82a-44a1-8922-1185ec080fbf--kIIq4WfOwI3z: Bibliographic document metadata (Perinorm 1.000) (provision)
The bibliographic document metadata shall be provided by the supplier of the ReqIF™ file for a public standard (see 9.9).
- bib.al.original-language: en
- bib.dp.publication-date: 2025-03-01
- ids.document: 99200
- ids.element: o1749224057223-sub-8.1.1.4
- ids.language-synoptic: o1749224057223-sub-8.1.1.4
- ids.tracing: hash-3f4b2de0135e1de044a2c3ff95240f20fb8596c64f9b48cf26c9c256d0e6ebac
- obj.clause-number: 8.1.1.4
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-e5302f19e870446

###### tr--6d400e6f-d82a-44a1-8922-1185ec080fbf--Uz086qyjqTBz: Bibliographic document metadata (Perinorm 1.000) (provision)
The bibliographic document metadata are the fourth block of the data model since accesses to the meta data of the original document are assumed to be less frequent.
- bib.al.original-language: en
- bib.dp.publication-date: 2025-03-01
- ids.document: 99200
- ids.element: o1749224057223-sub-8.1.1.4
- ids.language-synoptic: o1749224057223-sub-8.1.1.4
- ids.tracing: hash-ebe113917067a51a39b39f3d37d0e6b1d85b02a598eb1c5c16049bf1a75e11dc
- obj.clause-number: 8.1.1.4
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

###### tr--6d400e6f-d82a-44a1-8922-1185ec080fbf--qoKLexQOVCK1: Bibliographic document metadata (Perinorm 1.000) (provision)
The users can use the bibliographic document metadata to filter, search and manage provisions.
- bib.al.original-language: en
- bib.dp.publication-date: 2025-03-01
- ids.document: 99200
- ids.element: o1749224057223-sub-8.1.1.4
- ids.language-synoptic: o1749224057223-sub-8.1.1.4
- ids.tracing: hash-735253a23b3edea00ea489b0f6b520e1546703cb469fd9b6ee90ffb91197b982
- obj.clause-number: 8.1.1.4
- obj.element-name: paragraph
- obj.language: en
- obj.modality: permission
- obj.normativity: normative
- obj.specobject-type: provision
- obj.transformation-issues: Possibly wrong modal verb
- use.business-process: undefined
- use.business-sector: undefined
- use.interaction: undefined
- use.location: undefined
- use.product-category: undefined
- use.product-life-cycle: undefined
- use.project-phase: undefined
- use.purpose: undefined

###### prov-100000012-9f1bd30f0c8945e: Bibliographic document metadata (Perinorm 1.000), Note (provision)
NOTE:
The Metadata Field Specification of the Metadata Consortium supersedes the Perinorm Field Specification, published as: Perinorm Field Specification. Perinorm Consortium (AFNOR, BSI, DIN), 2009-11.
- bib.al.original-language: en
- bib.dp.publication-date: 2025-03-01
- ids.document: 99200
- ids.element: o1749224057223-sub-8.1.1.4
- ids.language-synoptic: o1749224057223-sub-8.1.1.4
- ids.tracing: hash-e12e44af66dd02cb5c4dd6f66e8d317f9488a03c3e901840b9c3255b2f1fe9cb
- obj.clause-number: 8.1.1.4
- obj.element-name: note
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

##### prov-100000012-5037242c7763499: Identification (ID) attributes on the provision (SpecObject) (heading)
- bib.al.original-language: en
- bib.dp.publication-date: 2025-03-01
- ids.document: 99200
- ids.element: o1749224057225-sub-8.1.1.5
- ids.language-synoptic: o1749224057225-sub-8.1.1.5
- ids.tracing: hash-cb98a1bf8aae68da561de0155367877bd16ad12849337d7c4067c375ad9a9345
- obj.clause-number: 8.1.1.5
- obj.element-name: heading
- obj.language: en
- obj.specobject-type: heading
- ChapterName: 8.1.1.5 Identification (ID) attributes on the provision (SpecObject)

###### tr--6d400e6f-d82a-44a1-8922-1185ec080fbf--IuFVL7VUC6LZ: Identification (ID) attributes on the provision (SpecObject) (provision)
The identification (ID) attributes (see 8.2.1.5) contain IDs for different user stories (see Clause B.1).
- bib.al.original-language: en
- bib.dp.publication-date: 2025-03-01
- ids.document: 99200
- ids.element: o1749224057225-sub-8.1.1.5
- ids.language-synoptic: o1749224057225-sub-8.1.1.5
- ids.tracing: hash-18a63537ed76f1900278bfb8ae0200d9ab4e2532c17e9910b09310515e6b9144
- obj.clause-number: 8.1.1.5
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-e252dcfc668b4dc
- cross-reference -> prov-100000012-cbe73fe9fbcd49b

###### tr--6d400e6f-d82a-44a1-8922-1185ec080fbf--2GNJfS9aaiPx: Identification (ID) attributes on the provision (SpecObject) (provision)
The identification (ID) attributes shall be provided by the supplier of the ReqIF™ file for a public standard (see 9.10).
- bib.al.original-language: en
- bib.dp.publication-date: 2025-03-01
- ids.document: 99200
- ids.element: o1749224057225-sub-8.1.1.5
- ids.language-synoptic: o1749224057225-sub-8.1.1.5
- ids.tracing: hash-eb41b60cedafae7fdd762f8a879151cabb0636fca2268731bee38849190f9bbe
- obj.clause-number: 8.1.1.5
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-038e236a0a004da

###### tr--6d400e6f-d82a-44a1-8922-1185ec080fbf--sCLLiiHSeSSk: Identification (ID) attributes on the provision (SpecObject) (provision)
The users can use the identification (ID) attributes to identify provisions, refer to provisions, manage and trace the change history of provisions.
- bib.al.original-language: en
- bib.dp.publication-date: 2025-03-01
- ids.document: 99200
- ids.element: o1749224057225-sub-8.1.1.5
- ids.language-synoptic: o1749224057225-sub-8.1.1.5
- ids.tracing: hash-8e05e56d84e8ab9c1896ad2d370ac88975c26a219af3287f3968f1538290e0cc
- obj.clause-number: 8.1.1.5
- obj.element-name: paragraph
- obj.language: en
- obj.modality: permission
- obj.normativity: normative
- obj.specobject-type: provision
- obj.transformation-issues: Possibly wrong modal verb
- use.business-process: undefined
- use.business-sector: undefined
- use.interaction: undefined
- use.location: undefined
- use.product-category: undefined
- use.product-life-cycle: undefined
- use.project-phase: undefined
- use.purpose: undefined

###### tr--6d400e6f-d82a-44a1-8922-1185ec080fbf--mLkrgoteDWjc: Identification (ID) attributes on the provision (SpecObject) (provision)
The identification (ID) attributes are the fifth block of the data model since accesses to identifiers of the original document are assumed to be less frequent.
- bib.al.original-language: en
- bib.dp.publication-date: 2025-03-01
- ids.document: 99200
- ids.element: o1749224057225-sub-8.1.1.5
- ids.language-synoptic: o1749224057225-sub-8.1.1.5
- ids.tracing: hash-fc0f92ce4b231e70982d32c159333beb3b7d62d708572ab537514a181ecee842
- obj.clause-number: 8.1.1.5
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-100000012-58f2305abf05458: Attributes on the document SpecObject for asset or service metadata of the creator, supplier, or publisher (heading)
- bib.al.original-language: en
- bib.dp.publication-date: 2025-03-01
- ids.document: 99200
- ids.element: o1749224057227-sub-8.1.2
- ids.language-synoptic: o1749224057227-sub-8.1.2
- ids.tracing: hash-1c816ab22f32696df29bdedfbcc338f4647c955034f5c55595f0757ae6ea7ec9
- obj.clause-number: 8.1.2
- obj.element-name: heading
- obj.language: en
- obj.specobject-type: heading
- ChapterName: 8.1.2 Attributes on the document SpecObject for asset or service metadata of the creator, supplier, or publisher

##### tr--6d400e6f-d82a-44a1-8922-1185ec080fbf--dEBMPNb9LBAd: Attributes on the document SpecObject for asset or service metadata of the creator, supplier, or publisher (provision)
The asset or service metadata (see 8.2.2) contain information from the creator, supplier, or publisher of the ReqIF™ file, such as name of the originator, release of this specification, name and version of the creating software.
- bib.al.original-language: en
- bib.dp.publication-date: 2025-03-01
- ids.document: 99200
- ids.element: o1749224057227-sub-8.1.2
- ids.language-synoptic: o1749224057227-sub-8.1.2
- ids.tracing: hash-7ce6a574d59972b29dc5f3a99776fdbc2819d51eb552da8e1a02f305d46c2d02
- obj.clause-number: 8.1.2
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-3f46a8f6af35401

##### tr--6d400e6f-d82a-44a1-8922-1185ec080fbf--eZl2PBnTG4iP: Attributes on the document SpecObject for asset or service metadata of the creator, supplier, or publisher (provision)
The bibliographic document metadata should be provided by the supplier of the ReqIF™ file for a public standard (see 9.11).
- bib.al.original-language: en
- bib.dp.publication-date: 2025-03-01
- ids.document: 99200
- ids.element: o1749224057227-sub-8.1.2
- ids.language-synoptic: o1749224057227-sub-8.1.2
- ids.tracing: hash-824ab356c98c5655f950b36ba7f19f1fe1056c9e0d24f569eae336dbe9c853f4
- obj.clause-number: 8.1.2
- obj.element-name: paragraph
- obj.language: en
- obj.modality: recommendation
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-18db2eab6e9f460

##### tr--6d400e6f-d82a-44a1-8922-1185ec080fbf--vNF1P8pTX0E2: Attributes on the document SpecObject for asset or service metadata of the creator, supplier, or publisher (provision)
The users can use the asset or service metadata to manage their processes and support issues.
- bib.al.original-language: en
- bib.dp.publication-date: 2025-03-01
- ids.document: 99200
- ids.element: o1749224057227-sub-8.1.2
- ids.language-synoptic: o1749224057227-sub-8.1.2
- ids.tracing: hash-0ceb353bd6f56092212da4cd357f855a3498652f4afb8dddaf7ab77272d86894
- obj.clause-number: 8.1.2
- obj.element-name: paragraph
- obj.language: en
- obj.modality: permission
- obj.normativity: normative
- obj.specobject-type: provision
- obj.transformation-issues: Possibly wrong modal verb
- use.business-process: undefined
- use.business-sector: undefined
- use.interaction: undefined
- use.location: undefined
- use.product-category: undefined
- use.product-life-cycle: undefined
- use.project-phase: undefined
- use.purpose: undefined

### prov-100000012-252f89746a5e4d1: Attributes (heading)
- bib.al.original-language: en
- bib.dp.publication-date: 2025-03-01
- ids.document: 99200
- ids.element: o1749224057230-sub-8.2
- ids.language-synoptic: o1749224057230-sub-8.2
- ids.tracing: hash-e9679fa5ec34507a841ad7608892ff3a19b7d3d256a5beea37fd4718ece428cb
- obj.clause-number: 8.2
- obj.element-name: heading
- obj.language: en
- obj.specobject-type: heading
- ChapterName: 8.2 Attributes

#### prov-100000012-19d8bd71411f4d8: Information on the provision (SpecObject) (heading)
- bib.al.original-language: en
- bib.dp.publication-date: 2025-03-01
- ids.document: 99200
- ids.element: o1749224057233-sub-8.2.1
- ids.language-synoptic: o1749224057233-sub-8.2.1
- ids.tracing: hash-8afa974073e294bb22cb21918e773c0862451cea28ae4c5e047b38d9c96377fc
- obj.clause-number: 8.2.1
- obj.element-name: heading
- obj.language: en
- obj.specobject-type: heading
- ChapterName: 8.2.1 Information on the provision (SpecObject)

##### prov-100000012-b3b3b3964862457: Content attributes on the provision (SpecObject) (heading)
- bib.al.original-language: en
- bib.dp.publication-date: 2025-03-01
- ids.document: 99200
- ids.element: o1749224057235-sub-8.2.1.1
- ids.language-synoptic: o1749224057235-sub-8.2.1.1
- ids.tracing: hash-eb23d71099b3aa842d6849af310f3990b8bd3d63ccf245795c9feb4fa9c7d687
- obj.clause-number: 8.2.1.1
- obj.element-name: heading
- obj.language: en
- obj.specobject-type: heading
- ChapterName: 8.2.1.1 Content attributes on the provision (SpecObject)

###### tr--6d400e6f-d82a-44a1-8922-1185ec080fbf--9ziJEAfoQNVh: Content attributes on the provision (SpecObject) (provision)
Content attributes see Table 1.
- bib.al.original-language: en
- bib.dp.publication-date: 2025-03-01
- ids.document: 99200
- ids.element: o1749224057235-sub-8.2.1.1
- ids.language-synoptic: o1749224057235-sub-8.2.1.1
- ids.tracing: hash-6aeb2bb4cd4a7e8710b0a889a46edf6bb66f1345bbbdf333015eb801866de210
- obj.clause-number: 8.2.1.1
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-7d10cdf1e32e43e

###### prov-100000012-7d10cdf1e32e43e: Content attributes (provision)
Table 1 — Content attributes
| data field term | ReqIF™ attribute name | ReqIF™ data type | occurrence | values | default | is-editable | location |  |  |  | definition | example |
| --- | --- | --- | --- | --- | --- | --- | --- | --- | --- | --- | --- | --- |
| data field term | ReqIF™ attribute name | ReqIF™ data type | occurrence | values | default | is-editable | document | heading | provision | specification | definition | example |
| Content | ReqIF.Text (content) | xhtml (32768) | zero or one | ~ | ~ | False | x |  | x |  | content of the SpecObject itself | ~ |
| Heading | ReqIF.ChapterName (heading) | xhtml (32768) | zero or one | ~ | ~ | False |  | x |  |  | content of the heading to the SpecObject | 1 Scope |
- bib.al.original-language: en
- bib.dp.publication-date: 2025-03-01
- ids.document: 99200
- ids.element: o1749224057235-tab-1
- ids.language-synoptic: o1749224057235-tab-1
- ids.tracing: hash-93679944e57080639902e80c80c3b7d8bad9a4d61acef7a9e9029553f6b859ac
- obj.clause-number: Table 1
- obj.element-name: table
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-2f90c5903f8d49c: Object attributes on the provision (SpecObject) (heading)
- bib.al.original-language: en
- bib.dp.publication-date: 2025-03-01
- ids.document: 99200
- ids.element: o1749224057237-sub-8.2.1.2
- ids.language-synoptic: o1749224057237-sub-8.2.1.2
- ids.tracing: hash-fe383cfbe2f45f11ef6bcec83dcc49a589fcc5993209d387ba17250d5bcf38fb
- obj.clause-number: 8.2.1.2
- obj.element-name: heading
- obj.language: en
- obj.specobject-type: heading
- ChapterName: 8.2.1.2 Object attributes on the provision (SpecObject)

###### tr--6d400e6f-d82a-44a1-8922-1185ec080fbf--8d0MiqQPfmmD: Object attributes on the provision (SpecObject) (provision)
Object attributes see Table 2.
- bib.al.original-language: en
- bib.dp.publication-date: 2025-03-01
- ids.document: 99200
- ids.element: o1749224057237-sub-8.2.1.2
- ids.language-synoptic: o1749224057237-sub-8.2.1.2
- ids.tracing: hash-3b2bce28ab5f671c903523ddb073bc57782ac92885532ded601dfaca7f6b039b
- obj.clause-number: 8.2.1.2
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-e988051c58d14d7

###### prov-100000012-e988051c58d14d7: Object attributes (provision)
Table 2 — Object attributes
| data field term | ReqIF™ attribute name | ReqIF™ data type | occurrence | values | default | is-editable | location |  |  |  | definition | example |
| --- | --- | --- | --- | --- | --- | --- | --- | --- | --- | --- | --- | --- |
| data field term | ReqIF™ attribute name | ReqIF™ data type | occurrence | values | default | is-editable | document | heading | provision | specification | definition | example |
| Clause context | obj.clause-number | string-64 | zero or one | ~ | ~ | false |  | x | x |  | label of the context like annex, clause, figure, or table if this is labelled or numbered | 1 |
| Clause heading | obj.clause-heading | string-1024 | zero or one | ~ | ~ | false |  | x | x |  | heading of an annex, clause, figure, or table if specified the text without the label or number | Scope |
| Reliability | obj.conversion-reliability | integer-percentage | one | ~ | ~ | false |  |  | x |  | estimated reliability of the automatic pre-classification in percent (0 % to 100 %) | 92 |
| Standard element | obj.element-name | enum-single | zero or one | 8.3.1 | ~ | true |  | x | x |  | role of the provision in a standard document, i. e. name of the element according to ISO/IEC Directives, Part 2 | warning |
| Language | obj.language | enum-single | one | 8.3.2 | ~ | true |  | x | x |  | language of the provision, expressed as lower-case 2-letter language code according to ISO 639 | en |
| Modality; bindingness | obj.modality | enum-single | zero or one | 8.3.3 | ~ | true |  |  | x |  | level of obligation for a governing provision in the standard model | requirement |
| Normativity; context status | obj.normativity | enum-single | one | 8.3.4 | ~ | true |  |  | x |  | normative or informative status for the context of a provision in the standard model | normative |
| SpecObject type | obj.specobject-type | enum-single | one | 8.3.5 | ~ | true | x | x | x |  | workaround for target systems which do not support different SpecObject types | content |
| Conversion issues | obj.transformation-issues | string-1024 | ~ | ~ | ~ | false | x | x | x | x | conversion issues generated by the supplier | not annotated |
- bib.al.original-language: en
- bib.dp.publication-date: 2025-03-01
- ids.document: 99200
- ids.element: o1749224057237-tab-2
- ids.language-synoptic: o1749224057237-tab-2
- ids.tracing: hash-5948444f8d296f4fda4741c2219312f309a1b8cee376077f5c0c703509ac47b8
- obj.clause-number: Table 2
- obj.element-name: table
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-dfd797af493c465
- cross-reference -> prov-100000012-b4b50b24a074457
- cross-reference -> prov-100000012-24f804847435467
- cross-reference -> prov-100000012-8040cc37e378430
- cross-reference -> prov-100000012-f22dd1ba13eb453

##### prov-100000012-84c18c91f471404: Use attributes for intra-company management of the provision (SpecObject) (heading)
- bib.al.original-language: en
- bib.dp.publication-date: 2025-03-01
- ids.document: 99200
- ids.element: o1749224057239-sub-8.2.1.3
- ids.language-synoptic: o1749224057239-sub-8.2.1.3
- ids.tracing: hash-fb7107a3276a62d520d01670fd2c14da58173c3f2cd8b5263f0f4fce39934d13
- obj.clause-number: 8.2.1.3
- obj.element-name: heading
- obj.language: en
- obj.specobject-type: heading
- ChapterName: 8.2.1.3 Use attributes for intra-company management of the provision (SpecObject)

###### tr--6d400e6f-d82a-44a1-8922-1185ec080fbf--9zYcJ9NwaruK: Use attributes for intra-company management of the provision (SpecObject) (provision)
Use attributes see Table 3.
- bib.al.original-language: en
- bib.dp.publication-date: 2025-03-01
- ids.document: 99200
- ids.element: o1749224057239-sub-8.2.1.3
- ids.language-synoptic: o1749224057239-sub-8.2.1.3
- ids.tracing: hash-c4f260d711d3f800b250da8a42ac80444a9be03a9152d3c80edb5dc35af6649b
- obj.clause-number: 8.2.1.3
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-adf1b9d4855b443

###### prov-100000012-adf1b9d4855b443: Use attributes (provision)
Table 3 — Use attributes
| data field term | ReqIF™ attribute name | ReqIF™ data type | occurrence | values | default | is-editable | location |  |  |  | definition | example |
| --- | --- | --- | --- | --- | --- | --- | --- | --- | --- | --- | --- | --- |
| data field term | ReqIF™ attribute name | ReqIF™ data type | occurrence | values | default | is-editable | document | heading | provision | specification | definition | example |
| Business process | use.business-process | enum-multi | zero or more | 8.3.6 | ~ | true |  |  | x |  | applicable business process where the provision is relevant | production; supporting – technology development |
| Business sector; industry sector | use.business-sector | enum-multi | zero or more | 8.3.7 | ~ | true |  |  | x |  | industry sector; applicable business sector where the provision is relevant | industrials – mechanical engineering |
| Date usage begins | use.date-usage-begins | string-64 | zero or one | ~ | ~ | true |  |  | x |  | applicable date when implementation of the provision is going to begin, expressed in the format YYYY-MM-DD according to DIN ISO 8601-1 | 2024-01-01 |
| Date usage ends | use.date-usage-ends | string-64 | zero or one | ~ | ~ | true |  |  | x |  | applicable date when implementation of the provision may terminate, expressed in the format YYYY-MM-DD according to DIN ISO 8601-1 | 2027-12-31 |
| Interaction | use.interaction | enum-multi | zero or one | 8.3.8 | ~ | true |  |  | x |  | type of interaction of the provision in the standard or use model | integral aspect |
| Implementation region | use.location | enum-multi | zero or more | 8.3.9 | ~ | true |  |  | x |  | geological locations where the provision is going to be implemented, expressed as lower-case ALPHA-3 country code according to DIN EN ISO 3166-1 | eee; usa |
| Project phase | use.project-phase | enum-multi | zero or more | 8.3.10 | ~ | true |  |  | x |  | applicable project phase where the provision is relevant | definition and planning; execution |
| Product category | use.product-category | string-1024 | zero or more | ~ | ~ | true |  |  | x |  | product group; product sector; applicable product category where the provision is relevant | roller bearings |
| Product life cycle | use.product-life-cycle | enum-multi | zero or more | 8.3.11 | ~ | true |  |  | x |  | phase (superseded); applicable phase in the life cycle of a product where the provision is relevant | design; recycling |
| Purpose; intention; focus | use.purpose | enum-multi | zero or more | 8.3.12 | ~ | true |  |  | x |  | function (superseded); primary scope of the provision | safety |
- bib.al.original-language: en
- bib.dp.publication-date: 2025-03-01
- ids.document: 99200
- ids.element: o1749224057239-tab-3
- ids.language-synoptic: o1749224057239-tab-3
- ids.tracing: hash-d6dcd6765a05e90a5d95f49ce90f4e22096c03c8bfc1591fbf97872ac9335404
- obj.clause-number: Table 3
- obj.element-name: table
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-715102bbf10144f
- cross-reference -> prov-100000012-f9a47e333ad1488
- cross-reference -> prov-100000012-16ded838180142e
- cross-reference -> prov-100000012-f9cfda6aa7d94b9
- cross-reference -> prov-100000012-2e7c42fa4bf848d
- cross-reference -> prov-100000012-d013c582f9b84bd
- cross-reference -> prov-100000012-2d82f4cb0f844c1

##### prov-100000012-ac76d054ec4c4b2: Bibliographic document metadata (Perinorm 1.000) (heading)
- bib.al.original-language: en
- bib.dp.publication-date: 2025-03-01
- ids.document: 99200
- ids.element: o1749224057241-sub-8.2.1.4
- ids.language-synoptic: o1749224057241-sub-8.2.1.4
- ids.tracing: hash-308189f9e61a67f24ad84d4c7ab779ebab05a25c92872d208192dfbfb06834ad
- obj.clause-number: 8.2.1.4
- obj.element-name: heading
- obj.language: en
- obj.specobject-type: heading
- ChapterName: 8.2.1.4 Bibliographic document metadata (Perinorm 1.000)

###### tr--6d400e6f-d82a-44a1-8922-1185ec080fbf--XQYuwOkhhMVB: Bibliographic document metadata (Perinorm 1.000) (provision)
Bibliographic document metadata see Table 4.
- bib.al.original-language: en
- bib.dp.publication-date: 2025-03-01
- ids.document: 99200
- ids.element: o1749224057241-sub-8.2.1.4
- ids.language-synoptic: o1749224057241-sub-8.2.1.4
- ids.tracing: hash-36973fce3a5c5004ed082cf98c5d9f30896ec2606b922f74ca2bb0e6f1cbc048
- obj.clause-number: 8.2.1.4
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-3345e5155a1e4ec

###### prov-100000012-3345e5155a1e4ec: Bibliographic document metadata (provision)
Table 4 — Bibliographic document metadata
| data field term | ReqIF™ attribute name | ReqIF™ data type | occurrence | values | default | is-editable | location |  |  |  | definition | example |
| --- | --- | --- | --- | --- | --- | --- | --- | --- | --- | --- | --- | --- |
| data field term | ReqIF™ attribute name | ReqIF™ data type | occurrence | values | default | is-editable | document | heading | provision | specification | definition | example |
| Document identifier | bib.di.document-identifier | string-1024 | one | ^ ^a | ~ | false | x | x | x |  | document number as given in the Perinorm sources like the DITR database | ISO 1463 |
| Publication date | bib.dp.publication-date | string-64 | zero or one | ^ ^a | ~ | false | x | x | x |  | publication date | 1982-07-00 |
| Update flag | bib.up.update-flag | string-1024 | one | ^ ^a | ~ | false | x |  | x |  | update flag from Perinorm | ~ |
| Document type | bib.ts.document-type | string-64 | one | ^ ^a | ~ | false | x |  | x |  | document type in Perinorm stage codes | ST*N |
| Title (German) | bib.tg.title-german | xhtml (2048) | zero or one | ^ ^a | ~ | false | x |  | x |  | title in German language | Metall- und Oxidschichten – Schichtdickenmessung – Mikroskopisches Verfahren |
| Title (English) | bib.ti.title-english | xhtml (2048) | zero or one | ^ ^a | ~ | false | x |  | x |  | title in English language | Metallic and oxide coatings – Measurement of coating thickness – Microscopical method |
| Title (French) | bib.tf.title-french | xhtml (2048) | zero or one | ^ ^a | ~ | false | x |  | x |  | title in French language | Revêtements métalliques et couches d’oxydes – Mesurage de l’épaisseur – Méthode par coupe micrographique |
| Replaced by | bib.rx.replaced-by | string-16384 | one | ^ ^a | ~ | false | x |  | x |  | document is replaced by newer edition | ISO 1463 (2003-03) |
| Replaces | bib.rz.replaces | string-16384 | zero or one | ^ ^a | ~ | false | x |  | x |  | document replaces previous edition | ISO 1463 (1973-02) |
| Amended by | bib.az.amended-by | string-16384 | zero or one | ^ ^a | ~ | false | x |  | x |  | document is amended by newer edition | ~ |
| Amends | bib.as.amends | string-16384 | zero or one | ^ ^a | ~ | false | x |  | x |  | document amends previous edition | ~ |
| Classification | bib.ca.classification | string-1024 | zero or one | ^ ^a | ~ | false | x |  | x |  | classification like ICS, UDC, DK, ISBN, or others | ICS 17.040.20 Properties of surfaces*ICS 25.220.40 Metallic coatings |
| Original language | bib.al.original-language | string-1024 | one | ^ ^a | ~ | false | x |  | x |  | language of the original publication | en |
| Descriptors (German) | bib.ct.descriptors-german | string-16384 | zero or one | ^ ^a | ~ | false | x |  | x |  | keywords in German language | Metallschicht*Methode*Prüfung*Schichtdickenmessung*Überzug*Design*Begriffe*Oxidschicht*Untersuchungsergebnis*Maß*Prüfergebn… |
| Descriptors (English) | bib.et.descriptors-english | string-16384 | zero or one | ^ ^a | ~ | false | x |  | x |  | keywords in English language | Materials testing*Microscopic analysis*Microscopes*Test results*Layer thickness measurement*Processes*Oxide coatings*Coatings*Meas… |
| Descriptors (French) | bib.ft.descriptors-french | string-16384 | zero or one | ^ ^a | ~ | false | x |  | x |  | keywords in French language | Procédure d’étalonnage*Mesure de l’épaisseur du revêtement*Email vitrifié*Email de porcelaine*Revêtement métallique*Présentation*Es… |
| International relationship | bib.ii.international-relationship | string-16384 | zero or one | ^ ^a | ~ | false | x |  | x |  | international relationship to other publications | EN ISO 1463 (1994-10), IDT*ISO 1463 (1982-07), IDT*ISO/DIS 1463 (1999-09), IDT*SN EN ISO 1463 (1995), IDT*TS 1542 EN ISO 1463 EN ISO 14 … |
| ^a Metadata Field Specification |  |  |  |  |  |  |  |  |  |  |  |  |
- bib.al.original-language: en
- bib.dp.publication-date: 2025-03-01
- ids.document: 99200
- ids.element: o1749224057241-tab-4
- ids.language-synoptic: o1749224057241-tab-4
- ids.tracing: hash-9314d95229231d8553f1daed37ef3ef203e0e1a8ead900a06d4ff4d17db06364
- obj.clause-number: Table 4
- obj.element-name: table
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

###### prov-100000012-a973ae91b3d2431: Bibliographic document metadata (provision)
| → table footnote | \| ^a Metadata Field Specification \| \| --- \| |
| --- | --- |
- bib.al.original-language: en
- bib.dp.publication-date: 2025-03-01
- ids.document: 99200
- ids.element: o1749224057241-tab-4
- ids.language-synoptic: o1749224057241-tab-4
- ids.tracing: hash-afece9d839dfe15b0b57e7efa10f16cd7cd75383c5d609299afbaa182f468ea3
- obj.clause-number: Table 4
- obj.element-name: footnote
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

##### prov-100000012-e252dcfc668b4dc: Identification (ID) attributes on the provision (SpecObject) (heading)
- bib.al.original-language: en
- bib.dp.publication-date: 2025-03-01
- ids.document: 99200
- ids.element: o1749224057243-sub-8.2.1.5
- ids.language-synoptic: o1749224057243-sub-8.2.1.5
- ids.tracing: hash-74962c0c49e196f40ef9e498479b878c68d2c1c99c98768cc83a0884afb4407b
- obj.clause-number: 8.2.1.5
- obj.element-name: heading
- obj.language: en
- obj.specobject-type: heading
- ChapterName: 8.2.1.5 Identification (ID) attributes on the provision (SpecObject)

###### tr--6d400e6f-d82a-44a1-8922-1185ec080fbf--WaLv3CypgHiC: Identification (ID) attributes on the provision (SpecObject) (provision)
Identification (ID) attributes see Table 5.
- bib.al.original-language: en
- bib.dp.publication-date: 2025-03-01
- ids.document: 99200
- ids.element: o1749224057243-sub-8.2.1.5
- ids.language-synoptic: o1749224057243-sub-8.2.1.5
- ids.tracing: hash-19f32aa7f2f4451c7fa884746158efa0ac01513df3eed33e76fb66971dfff849
- obj.clause-number: 8.2.1.5
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-3930d9a42bb4495

###### prov-100000012-3930d9a42bb4495: Identification (ID) attributes (provision)
Table 5 — Identification (ID) attributes
| data field term | ReqIF™ attribute name | ReqIF™ data type | occurrence | values | default | is-editable | location |  |  |  | definition | example |
| --- | --- | --- | --- | --- | --- | --- | --- | --- | --- | --- | --- | --- |
| data field term | ReqIF™ attribute name | ReqIF™ data type | occurrence | values | default | is-editable | document | heading | provision | specification | definition | example |
| Document ID | ids.document | string-64 | zero or one | ~ | ~ | false | x | x | x |  | identifier which is unique for same version of the same document, e. g., using machine-resolvable database keys like the XML key (FIDAS key) | e11d82e5 |
| Element ID | ids.element | string-64 | zero or one | ~ | ~ | false |  | x | x |  | identifier which is unique for the same fragment within the same version of the same document, e. g., speaking identifiers (IDs) | fig-3a, sub-5.2.1, tab-na.1, … |
| Language-independent ID | ids.language-synoptic | string-64 | zero or one | ~ | ~ | false |  | x | x |  | identifier which is unique for the same fragment across all language variants within the same version of the same document | ~ |
| Version-independent tracing ID | ids.tracing | string-1024 | zero or one | ~ | ~ | false |  | x | x |  | identifier which is unique for the same content of the same fragment across all versions of the same document | fb53c22e-01b2-5dd7-98cb-bf2236977775 |
| XPath end | ids.xpath-end | string-1024 | zero or one | ~ | ~ | false |  |  | x |  | XPath into the XML source instance where the provision ends | /adoption[1]/adoption-front[1]/sec[1]/p[1] |
| XPath start | ids.xpath-start | string-1024 | zero or one | ~ | ~ | false |  |  | x |  | XPath into the XML source instance where the provision starts | /adoption[1]/adoption-front[1]/sec[1]/p[1] |
| Version-dependent unique ID | ids.unique | string-1024 | zero or one | ~ | ~ | false |  | x | x |  | identifier which is globally (GUID) or universally (UUID) unique for each fragment across all documents and versions of these | tr--e11d82e5--sub-3.2.1--42 |
- bib.al.original-language: en
- bib.dp.publication-date: 2025-03-01
- ids.document: 99200
- ids.element: o1749224057243-tab-5
- ids.language-synoptic: o1749224057243-tab-5
- ids.tracing: hash-ebb121d9d94788207f6b5cdb2159651d6bf04035285dd2ba70677c38425dfc92
- obj.clause-number: Table 5
- obj.element-name: table
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-100000012-3f46a8f6af35401: Attributes on the document SpecObject for asset or service metadata of the creator, supplier, or publisher (heading)
- bib.al.original-language: en
- bib.dp.publication-date: 2025-03-01
- ids.document: 99200
- ids.element: o1749224057245-sub-8.2.2
- ids.language-synoptic: o1749224057245-sub-8.2.2
- ids.tracing: hash-33736af5672de4989a300ff9cc03c80b14742b237a75432604e3758b7c1a2d9f
- obj.clause-number: 8.2.2
- obj.element-name: heading
- obj.language: en
- obj.specobject-type: heading
- ChapterName: 8.2.2 Attributes on the document SpecObject for asset or service metadata of the creator, supplier, or publisher

##### tr--6d400e6f-d82a-44a1-8922-1185ec080fbf--Aj32U7tVgctO: Attributes on the document SpecObject for asset or service metadata of the creator, supplier, or publisher (provision)
Attributes on the document SpecObject see Table 6.
- bib.al.original-language: en
- bib.dp.publication-date: 2025-03-01
- ids.document: 99200
- ids.element: o1749224057245-sub-8.2.2
- ids.language-synoptic: o1749224057245-sub-8.2.2
- ids.tracing: hash-dd311387b1eff03bd14071cd81a209c8ed06efa7819528f7c367427bd82e26bf
- obj.clause-number: 8.2.2
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-904190e016324c0

##### prov-100000012-904190e016324c0: Attributes on the document SpecObject (provision)
Table 6 — Attributes on the document SpecObject
| data field term | ReqIF™ attribute name | ReqIF™ data type | occurrence | values | default | is-editable | location |  |  |  | definition | example |
| --- | --- | --- | --- | --- | --- | --- | --- | --- | --- | --- | --- | --- |
| data field term | ReqIF™ attribute name | ReqIF™ data type | occurrence | values | default | is-editable | document | heading | provision | specification | definition | example |
| Originator | pub.originator | string-64 | one or more | ~ | ~ | false | x |  |  |  | abbreviation or short name of the originator, for example DIN, DKE, etc. | DIN*DKE*IEC*ISO |
| Harmonization | pub.harmonization | string-64 | one | ~ |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 example | false | x |  |  |  | harmonization string for the level of harmonization and version number | IDiS ReqIF™ interpretation for public standards 1.3 |
| Software | pub.software | string-64 | zero or one | ~ |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 example | false | x |  |  |  | identification string for software + version | X-Swift sts2reqif-42.17.4 |
| Supplier | pub.supplier | string-64 | one or more | ~ | ~ | false | x |  |  |  | abbreviation or short name of the supplier, for example DIN Media, VDE VERLAG, etc. | - • • DIN Media - • • VDE VERLAG |
- bib.al.original-language: en
- bib.dp.publication-date: 2025-03-01
- ids.document: 99200
- ids.element: o1749224057245-tab-6
- ids.language-synoptic: o1749224057245-tab-6
- ids.tracing: hash-b415f54abdac0ea56aade17ea4d6fd750830326cb52d4816e51135904512dbbb
- obj.clause-number: Table 6
- obj.element-name: table
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-100000012-62b877911c1c4ff: Lists of attribute values (heading)
- bib.al.original-language: en
- bib.dp.publication-date: 2025-03-01
- ids.document: 99200
- ids.element: o1749224057248-sub-8.3
- ids.language-synoptic: o1749224057248-sub-8.3
- ids.tracing: hash-ef79e2db7e543f61e001d9d7dcf9b011f940ea458e9a068f7fb2905edc7823ea
- obj.clause-number: 8.3
- obj.element-name: heading
- obj.language: en
- obj.specobject-type: heading
- ChapterName: 8.3 Lists of attribute values

#### prov-100000012-dfd797af493c465: Standard element (obj.element-name) (heading)
- bib.al.original-language: en
- bib.dp.publication-date: 2025-03-01
- ids.document: 99200
- ids.element: o1749224057250-sub-8.3.1
- ids.language-synoptic: o1749224057250-sub-8.3.1
- ids.tracing: hash-dc591613401e849043e12a66749aabcbfe053995bc69e1034c5f19a3d03a1e85
- obj.clause-number: 8.3.1
- obj.element-name: heading
- obj.language: en
- obj.specobject-type: heading
- ChapterName: 8.3.1 Standard element (obj.element-name)

##### tr--6d400e6f-d82a-44a1-8922-1185ec080fbf--kQdGa3daojfr: Standard element (obj.element-name) (provision)
Attribute values see Table 7.
- bib.al.original-language: en
- bib.dp.publication-date: 2025-03-01
- ids.document: 99200
- ids.element: o1749224057250-sub-8.3.1
- ids.language-synoptic: o1749224057250-sub-8.3.1
- ids.tracing: hash-b009d8e471366c3f64fae565fe4ba8c475e2038c1bccc16fb602b84be7279157
- obj.clause-number: 8.3.1
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-c562006bd71e4c4

##### prov-100000012-c562006bd71e4c4: Values for the attribute obj.element-name (provision)
Table 7 — Values for the attribute obj.element-name
| values | definition |
| --- | --- |
| block | block with boxed text within a publication |
| caption | caption within a figure or table |
| concept | concept, i. e. container with terms and definition according to DIN ISO 10241-1 |
| descriptive-list | descriptive list (<dl> type enumeration) |
| display-formula | displayed formula |
| document | document, indicates that no other element could be determined |
| example | example |
| figure | figure (with caption) |
| footnote | footnote |
| formula | formula, i. e. inline formula signs or units) |
| graphics | graphics (without caption) |
| heading | heading of an annex, clause, or other type of division |
| legend | legend within a figure |
| list-of-documents | list of documents in the Normative References or Bibliography |
| note | note |
| ordered-list | ordered list (<ol> type enumeration) |
| ordering-details | ordering details (designation system) |
| paragraph | paragraph |
| printed-form | printed form |
| profile | metadata or title page |
| quotation | quotation, i. e. displayed text quoted from another source |
| signature | signature within a legal standard |
| standard-designation | standard designation (designation system) |
| table | table (with caption) |
| tabular-form | tabular form or informal table (without caption) |
| typed-form | typed form, i. e. computer code or typewriter text (monospaced) |
| undefined | default option if required and no value has been provided |
| units | units within a figure or table |
| unordered-list | unordered list (<ul> type enumeration) |
| warning | Warning |
- bib.al.original-language: en
- bib.dp.publication-date: 2025-03-01
- ids.document: 99200
- ids.element: o1749224057250-tab-7
- ids.language-synoptic: o1749224057250-tab-7
- ids.tracing: hash-3541ba753084beeeab942b0fc4a7e90ad6985c5bef4b996d22eef88fd4eb7590
- obj.clause-number: Table 7
- obj.element-name: table
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-100000012-b4b50b24a074457: Language (obj.language) (heading)
- bib.al.original-language: en
- bib.dp.publication-date: 2025-03-01
- ids.document: 99200
- ids.element: o1749224057252-sub-8.3.2
- ids.language-synoptic: o1749224057252-sub-8.3.2
- ids.tracing: hash-d7dc7c0c63b92d5efcb28bbc211438f93e6e537776e0bd19d0f7809292c77186
- obj.clause-number: 8.3.2
- obj.element-name: heading
- obj.language: en
- obj.specobject-type: heading
- ChapterName: 8.3.2 Language (obj.language)

##### tr--6d400e6f-d82a-44a1-8922-1185ec080fbf--iwM3517OBwxI: Language (obj.language) (provision)
Attribute values see Table 8.
- bib.al.original-language: en
- bib.dp.publication-date: 2025-03-01
- ids.document: 99200
- ids.element: o1749224057252-sub-8.3.2
- ids.language-synoptic: o1749224057252-sub-8.3.2
- ids.tracing: hash-2f675f4990655268d8bd03b043a18196694cb11b43433ccd3c08b57a45945224
- obj.clause-number: 8.3.2
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-1522997c97d54e1

##### prov-100000012-1522997c97d54e1: Values for the attribute obj.language (provision)
Table 8 — Values for the attribute obj.language
| values | definition |
| --- | --- |
| ar | Arabic |
| be | Belarusian |
| bg | Bulgarian |
| bs | Bosnian |
| cs | Czech |
| da | Danish |
| de | German |
| el | Greek, modern ~ |
| en | English |
| es | Spanish, Castilian |
| et | Estonian |
| fi | Finnish |
| fr | French |
| ga | Irish |
| he | Hebrew |
| hr | Croatian |
| hu | Hungarian |
| id | Indonesian |
| is | Icelandic |
| it | Italian |
| ja | Japanese |
| ka | Georgian |
| ko | Korean |
| lb | Luxembourgish, Letzeburgesch |
| lt | Lithuanian |
| lv | Latvian |
| mk | Macedonian |
| mt | Maltese |
| nl | Dutch, Flemish |
| no | Norwegian |
| pl | Polish |
| pt | Portuguese |
| ro | Romanian, Moldavian, Moldovan |
| ru | Russian |
| sk | Slovak |
| sl | Slovenian |
| sq | Albanian |
| sr | Serbian |
| sv | Swedish |
| tr | Turkish |
| uk | Ukrainian |
| undefined | default option if required and no value has been provided |
| vi | Vietnamese |
| zh | Chinese |
- bib.al.original-language: en
- bib.dp.publication-date: 2025-03-01
- ids.document: 99200
- ids.element: o1749224057252-tab-8
- ids.language-synoptic: o1749224057252-tab-8
- ids.tracing: hash-6962211ed4fb0be741656806a7380be1e959b49a0878b3f073b5918d77b45eb8
- obj.clause-number: Table 8
- obj.element-name: table
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-100000012-24f804847435467: Modality; bindingness (obj.modality) (heading)
- bib.al.original-language: en
- bib.dp.publication-date: 2025-03-01
- ids.document: 99200
- ids.element: o1749224057254-sub-8.3.3
- ids.language-synoptic: o1749224057254-sub-8.3.3
- ids.tracing: hash-dfa41fd204158213fa14fe51fdf15dc81e9d37a314b25126dd5b6dc202c716c3
- obj.clause-number: 8.3.3
- obj.element-name: heading
- obj.language: en
- obj.specobject-type: heading
- ChapterName: 8.3.3 Modality; bindingness (obj.modality)

##### tr--6d400e6f-d82a-44a1-8922-1185ec080fbf--xyySnJ6Be3X7: Modality; bindingness (obj.modality) (provision)
Attribute values see Table 9.
- bib.al.original-language: en
- bib.dp.publication-date: 2025-03-01
- ids.document: 99200
- ids.element: o1749224057254-sub-8.3.3
- ids.language-synoptic: o1749224057254-sub-8.3.3
- ids.tracing: hash-b2096d4d494cee007c4c9b640c6456eed388066763e1ce0e2ed0105831b76608
- obj.clause-number: 8.3.3
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-f6bb86e35c04454

##### prov-100000012-f6bb86e35c04454: Values for the attribute obj.modality (provision)
Table 9 — Values for the attribute obj.modality
| values | definition |
| --- | --- |
| ambiguous | modality is ambiguous, e. g., there are multiple or unclear variant occurrences for the modality |
| capability | expression that conveys the ability, fitness, or quality necessary to do or achieve a specified thing (ISO/IEC Directives, Part 2) |
| constraint | external constraint or obligation on the user of the document that is not stated as a provision of the document, e. g., laws of nature or particular conditions existing in some countries or regions (ISO/IEC Directives, Part 2) |
| permission | expression that conveys consent or liberty (or opportunity) to do something (ISO/IEC Directives, Part 2) |
| possibility | expression that conveys expected or conceivable material, physical or causal outcome (ISO/IEC Directives, Part 2) |
| recommendation | expression that conveys a suggested possible choice or course of action deemed to be particularly suitable without necessarily mentioning or excluding others (ISO/IEC Directives, Part 2) |
| requirement | expression that conveys objectively verifiable criteria to be fulfilled and from which no deviation is permitted if conformance with the document is to be claimed (ISO/IEC Directives, Part 2) |
| undefined | modality is undefined, e. g., modality of the provision has not been explicitly evaluated |
- bib.al.original-language: en
- bib.dp.publication-date: 2025-03-01
- ids.document: 99200
- ids.element: o1749224057254-tab-9
- ids.language-synoptic: o1749224057254-tab-9
- ids.tracing: hash-6f6340008ee7313f96ebf67f2fccb2dd9367b96ab7ec5872d0c31b31097c9402
- obj.clause-number: Table 9
- obj.element-name: table
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-100000012-8040cc37e378430: Normativity; context status (obj.normativity) (heading)
- bib.al.original-language: en
- bib.dp.publication-date: 2025-03-01
- ids.document: 99200
- ids.element: o1749224057256-sub-8.3.4
- ids.language-synoptic: o1749224057256-sub-8.3.4
- ids.tracing: hash-31aa9bc88a7c908e8e1d62a75dc45e7417def330b70c152aa23e5e859f18df1f
- obj.clause-number: 8.3.4
- obj.element-name: heading
- obj.language: en
- obj.specobject-type: heading
- ChapterName: 8.3.4 Normativity; context status (obj.normativity)

##### tr--6d400e6f-d82a-44a1-8922-1185ec080fbf--Wge3oydN0hMR: Normativity; context status (obj.normativity) (provision)
Attribute values see Table 10.
- bib.al.original-language: en
- bib.dp.publication-date: 2025-03-01
- ids.document: 99200
- ids.element: o1749224057256-sub-8.3.4
- ids.language-synoptic: o1749224057256-sub-8.3.4
- ids.tracing: hash-ea18990fad0d89afe91466f3d13e9373ebb42a94dcf8c271cbab2dbadceb7c9d
- obj.clause-number: 8.3.4
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-1fd1868250bb49b

##### prov-100000012-1fd1868250bb49b: Values for the attribute obj.normativity (provision)
Table 10 — Values for the attribute obj.normativity
| values | definition |
| --- | --- |
| informative | context is an informative element, e. g., annex (informative), example, foreword, introduction, note |
| normative | context is a normative element, e. g., annex (normative) |
| undefined | default option if required and no value has been provided |
- bib.al.original-language: en
- bib.dp.publication-date: 2025-03-01
- ids.document: 99200
- ids.element: o1749224057256-tab-10
- ids.language-synoptic: o1749224057256-tab-10
- ids.tracing: hash-7d3011b5b3fae7ec61ec0bfd3a52fb787164b8958ffd81a1cdbd15fe698078f4
- obj.clause-number: Table 10
- obj.element-name: table
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-100000012-f22dd1ba13eb453: SpecObject type (obj.specobj-type) (heading)
- bib.al.original-language: en
- bib.dp.publication-date: 2025-03-01
- ids.document: 99200
- ids.element: o1749224057258-sub-8.3.5
- ids.language-synoptic: o1749224057258-sub-8.3.5
- ids.tracing: hash-d9a2ab279b6d090400c5efa4347531b0890c2fa085d87d3a62ef9f4f30e47df7
- obj.clause-number: 8.3.5
- obj.element-name: heading
- obj.language: en
- obj.specobject-type: heading
- ChapterName: 8.3.5 SpecObject type (obj.specobj-type)

##### tr--6d400e6f-d82a-44a1-8922-1185ec080fbf--Nk87C701SiYp: SpecObject type (obj.specobj-type) (provision)
Attribute values see Table 11.
- bib.al.original-language: en
- bib.dp.publication-date: 2025-03-01
- ids.document: 99200
- ids.element: o1749224057258-sub-8.3.5
- ids.language-synoptic: o1749224057258-sub-8.3.5
- ids.tracing: hash-9d3bb7c2ece46ff50edef6026758d0c439c73252c82835a79ee1ba2af0d31cb2
- obj.clause-number: 8.3.5
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-400ea64a3d30448

##### prov-100000012-400ea64a3d30448: Values for the attribute obj.specobj-type (provision)
Table 11 — Values for the attribute obj.specobj-type
| values | definition |
| --- | --- |
| document | content of the profile to the SpecObject (title page) |
| heading | content of the heading to the SpecObject |
| provision | content of the SpecObject itself |
| undefined | default option if required and no value has been provided |
- bib.al.original-language: en
- bib.dp.publication-date: 2025-03-01
- ids.document: 99200
- ids.element: o1749224057258-tab-11
- ids.language-synoptic: o1749224057258-tab-11
- ids.tracing: hash-4d84a0e9c3de860da90a437cfb042cb74a17df505ee59f8e8bef3410351d3243
- obj.clause-number: Table 11
- obj.element-name: table
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-100000012-715102bbf10144f: Business process (use.business-process) (heading)
- bib.al.original-language: en
- bib.dp.publication-date: 2025-03-01
- ids.document: 99200
- ids.element: o1749224057260-sub-8.3.6
- ids.language-synoptic: o1749224057260-sub-8.3.6
- ids.tracing: hash-050bb183b392e4db222ca494e0d2c267e0707c5a7198b0b95e9269ea9f3c54f8
- obj.clause-number: 8.3.6
- obj.element-name: heading
- obj.language: en
- obj.specobject-type: heading
- ChapterName: 8.3.6 Business process (use.business-process)

##### tr--6d400e6f-d82a-44a1-8922-1185ec080fbf--igYuWqvIl52G: Business process (use.business-process) (provision)
Attribute values see Table 12.
- bib.al.original-language: en
- bib.dp.publication-date: 2025-03-01
- ids.document: 99200
- ids.element: o1749224057260-sub-8.3.6
- ids.language-synoptic: o1749224057260-sub-8.3.6
- ids.tracing: hash-3cc9c26989cf3a0319ff4e30da3cbee6c39abebae7f81b2bb9636a0d8d2fdc7f
- obj.clause-number: 8.3.6
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-c93d50da1c3346b

##### prov-100000012-c93d50da1c3346b: Values for the attribute use-business-process (provision)
Table 12 — Values for the attribute use-business-process
| values | definition |
| --- | --- |
| logistics external | logistics outbound; activities deliver your product or service to your customer; these are things like collection, storage, and distribution systems, and they may be internal or external to your organization [9] |
| logistics internal | logistics inbound; processes related to receiving, storing, and distributing inputs internally; your supplier relationships are a key factor in creating value here [9] |
| marketing and sales | processes you use to persuade clients to purchase from you instead of your competitors; the benefits you offer, and how well you communicate them, are sources of value here [9] |
| production | operations; transformation activities that change inputs into outputs that are sold to customers; here, your operational systems create value [9] |
| service | activities related to maintaining the value of your product or service to your customers, once it’s been purchased [9] |
| supporting – acquisition | purchasing processes |
| supporting – corporate infrastructure | infrastructure |
| supporting – human resource management | personal department processes |
| supporting – technology development | development |
| undefined | default option if required and no value has been provided |
- bib.al.original-language: en
- bib.dp.publication-date: 2025-03-01
- ids.document: 99200
- ids.element: o1749224057260-tab-12
- ids.language-synoptic: o1749224057260-tab-12
- ids.tracing: hash-67c934d010894246c8cb4eb6ecd8079dd5c8c3317b5238c26d22253a74ce2f64
- obj.clause-number: Table 12
- obj.element-name: table
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-402e6ac107ee49d

#### prov-100000012-f9a47e333ad1488: Business sector; industry sector (use.business-sector) (heading)
- bib.al.original-language: en
- bib.dp.publication-date: 2025-03-01
- ids.document: 99200
- ids.element: o1749224057262-sub-8.3.7
- ids.language-synoptic: o1749224057262-sub-8.3.7
- ids.tracing: hash-1447cc2d90444cf1c50673cdfe855561b7b42af7c20648f9f149cd9632ccc69c
- obj.clause-number: 8.3.7
- obj.element-name: heading
- obj.language: en
- obj.specobject-type: heading
- ChapterName: 8.3.7 Business sector; industry sector (use.business-sector)

##### tr--6d400e6f-d82a-44a1-8922-1185ec080fbf--oXTDEMdLYvmB: Business sector; industry sector (use.business-sector) (provision)
Attribute values see Table 13.
- bib.al.original-language: en
- bib.dp.publication-date: 2025-03-01
- ids.document: 99200
- ids.element: o1749224057262-sub-8.3.7
- ids.language-synoptic: o1749224057262-sub-8.3.7
- ids.tracing: hash-4a1b37f3d84d13e545be6a113e7ccab6817f3b9a900bf4a2b84b541b1217da43
- obj.clause-number: 8.3.7
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-d484700662144d9

##### prov-100000012-d484700662144d9: Values for the attribute use.business-sector (provision)
Table 13 — Values for the attribute use.business-sector
| values | definition |
| --- | --- |
| building | building sector |
| consumer discretionary | consumer discretionary sector |
| consumer services | consumer services sector |
| consumer staples | consumer staples sector |
| energy | energy sector |
| financials | financials sector |
| healthcare | healthcare sector |
| industrials – aerospace | industrials – aerospace sector |
| industrials – automotive | industrials – automotive sector |
| industrials – defense | industrials – defense sector |
| industrials – electrical engineering | industrials – electrical engineering sector |
| industrials – mechanical engineering | industrials – mechanical engineering sector |
| industrials – medical engineering | industrials – medical engineering sector |
| materials | materials sector |
| other | other sector |
| real estate | real estate sector |
| services | services sector |
| technology | technology sector |
| undefined | default option if required and no value has been provided |
| utilities | utilities sector |
- bib.al.original-language: en
- bib.dp.publication-date: 2025-03-01
- ids.document: 99200
- ids.element: o1749224057262-tab-13
- ids.language-synoptic: o1749224057262-tab-13
- ids.tracing: hash-12106a501085146699ad17461cccac0ec686dec996bec03ab396727c76806b39
- obj.clause-number: Table 13
- obj.element-name: table
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-100000012-16ded838180142e: Interaction (use.interaction) (heading)
- bib.al.original-language: en
- bib.dp.publication-date: 2025-03-01
- ids.document: 99200
- ids.element: o1749224057264-sub-8.3.8
- ids.language-synoptic: o1749224057264-sub-8.3.8
- ids.tracing: hash-c03e102f9bb6aab43962c3d9130c6a4f3b3bbd1233fefc81a4d660bcd95c9a6d
- obj.clause-number: 8.3.8
- obj.element-name: heading
- obj.language: en
- obj.specobject-type: heading
- ChapterName: 8.3.8 Interaction (use.interaction)

##### tr--6d400e6f-d82a-44a1-8922-1185ec080fbf--xsqVU8M0ulRv: Interaction (use.interaction) (provision)
Attribute values see Table 14.
- bib.al.original-language: en
- bib.dp.publication-date: 2025-03-01
- ids.document: 99200
- ids.element: o1749224057264-sub-8.3.8
- ids.language-synoptic: o1749224057264-sub-8.3.8
- ids.tracing: hash-7223c3dfc4db6483a0070ab20706481745dc1d46ac09ded034c2e9e422e5485b
- obj.clause-number: 8.3.8
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-309bedaeb944435

##### prov-100000012-309bedaeb944435: Values for the attribute use.interaction (provision)
Table 14 — Values for the attribute use.interaction
| values | definition |
| --- | --- |
| activity | activity (process) |
| functional | functional (system) |
| integral aspect | integral aspect (system) |
| interface | interface (system) |
| undefined | default option if required and no value has been provided |
| verification | verification (method of proof) |
- bib.al.original-language: en
- bib.dp.publication-date: 2025-03-01
- ids.document: 99200
- ids.element: o1749224057264-tab-14
- ids.language-synoptic: o1749224057264-tab-14
- ids.tracing: hash-bdf2ff81cb054f00f73719e300563dd7ad22e5d1de85f1e28e91154a5ab97295
- obj.clause-number: Table 14
- obj.element-name: table
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-100000012-f9cfda6aa7d94b9: Implementation region (use.location) (heading)
- bib.al.original-language: en
- bib.dp.publication-date: 2025-03-01
- ids.document: 99200
- ids.element: o1749224057266-sub-8.3.9
- ids.language-synoptic: o1749224057266-sub-8.3.9
- ids.tracing: hash-6b1503bd07404806119b8f16771ae50b60e84dd8cce5f1cc6c2593b88f06a8b1
- obj.clause-number: 8.3.9
- obj.element-name: heading
- obj.language: en
- obj.specobject-type: heading
- ChapterName: 8.3.9 Implementation region (use.location)

##### tr--6d400e6f-d82a-44a1-8922-1185ec080fbf--h6CWlgkLrI1F: Implementation region (use.location) (provision)
Attribute values see Table 15.
- bib.al.original-language: en
- bib.dp.publication-date: 2025-03-01
- ids.document: 99200
- ids.element: o1749224057266-sub-8.3.9
- ids.language-synoptic: o1749224057266-sub-8.3.9
- ids.tracing: hash-9111e664f6d7cf0beb310d42e191779f82b16f999ba4af431a2d443b65e6a89d
- obj.clause-number: 8.3.9
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-5e1f220fa4fa4e4

##### prov-100000012-5e1f220fa4fa4e4: Values for the attribute use.location (provision)
Table 15 — Values for the attribute use.location
| values | definition |
| --- | --- |
| abb | Asia |
| alb | Albania |
| and | Andorra |
| atg | Antigua and Barbuda |
| aus | Australia |
| aut | Austria |
| bel | Belgium |
| bgr | Bulgaria |
| bhs | Bahamas |
| bih | Bosnia and Herzegovina |
| blr | Belarus |
| can | Canada |
| che | Switzerland |
| chn | China |
| cub | Cuba |
| cyp | Cyprus |
| cze | Czechia |
| deu | Germany |
| dnk | Denmark |
| eee | Europe |
| esp | Spain |
| est | Estonia |
| fff | Africa |
| fin | Finland |
| fra | France |
| gbr | United Kingdom of Great Britain and Northern Ireland |
| geo | Georgia |
| gib | Gibraltar |
| grc | Greece |
| hkg | China, Hong Kong Special Administrative Region |
| hrv | Croatia |
| hun | Hungary |
| idn | Indonesia |
| ind | India |
| irl | Ireland |
| isl | Iceland |
| isr | Israel |
| ita | Italy |
| jam | Jamaica |
| jpn | Japan |
| kgz | Kyrgyzstan |
| kor | Republic of Korea |
| kwt | Kuwait |
| lie | Liechtenstein |
| ltu | Lithuania |
| lux | Luxembourg |
| lva | Latvia |
| mco | Monaco |
| mda | Republic of Moldova |
| mkd | North Macedonia |
| mlt | Malta |
| mne | Montenegro |
| nld | The Netherlands |
| nnn | North America |
| nor | Norway |
| nzl | New Zealand |
| phl | Philippines |
| pol | Poland |
| prk | Democratic People’s Republic of Korea |
| prt | Portugal |
| rou | Romania |
| rus | Russian Federation |
| sau | Saudi Arabia |
| srb | Serbia |
| srr | South America |
| svk | Slovakia |
| svn | Slovenia |
| swe | Sweden |
| tjk | Tajikistan |
| tur | Türkiye; Turkey |
| twn | Taiwan (Province of China) |
| ukr | Ukraine |
| undefined | default option if required and no value has been provided |
| usa | United States of America |
| uuu | Oceania |
| vnm | Viet Nam; Vietnam |
| xkk | Kosovo |
- bib.al.original-language: en
- bib.dp.publication-date: 2025-03-01
- ids.document: 99200
- ids.element: o1749224057266-tab-15
- ids.language-synoptic: o1749224057266-tab-15
- ids.tracing: hash-6dc199ab488fa8a837418128aeedd0fd083027faf3df4f23ae6cd4902736755f
- obj.clause-number: Table 15
- obj.element-name: table
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-100000012-2e7c42fa4bf848d: Project phase (use.project-phase) (heading)
- bib.al.original-language: en
- bib.dp.publication-date: 2025-03-01
- ids.document: 99200
- ids.element: o1749224057268-sub-8.3.10
- ids.language-synoptic: o1749224057268-sub-8.3.10
- ids.tracing: hash-9dc6f33eb94f4c54b83d27cbc4334deadb69c093474cbfd428d7661fdfb5acca
- obj.clause-number: 8.3.10
- obj.element-name: heading
- obj.language: en
- obj.specobject-type: heading
- ChapterName: 8.3.10 Project phase (use.project-phase)

##### tr--6d400e6f-d82a-44a1-8922-1185ec080fbf--J3FnBeiZUIJH: Project phase (use.project-phase) (provision)
Attribute values see Table 16.
- bib.al.original-language: en
- bib.dp.publication-date: 2025-03-01
- ids.document: 99200
- ids.element: o1749224057268-sub-8.3.10
- ids.language-synoptic: o1749224057268-sub-8.3.10
- ids.tracing: hash-adf047e9ddac7c64400498994d7161ff59ee4a35c87e54ad9cfac167bea96050
- obj.clause-number: 8.3.10
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-bda0e53d31f9488

##### prov-100000012-bda0e53d31f9488: Values for the attribute use.project-phase (provision)
Table 16 — Values for the attribute use.project-phase
| Values | definition |
| --- | --- |
| close out | analyze and summarize the results to close out of the project |
| definition and planning | define tasks and timelines needed to execute the project |
| Execution | execute the project plan |
| Initiation | define project objectives, deadlines, priorities, chances, and risks |
| monitoring and control | monitor and control of the project progress |
| Undefined | default option if required and no value has been provided |
- bib.al.original-language: en
- bib.dp.publication-date: 2025-03-01
- ids.document: 99200
- ids.element: o1749224057268-tab-16
- ids.language-synoptic: o1749224057268-tab-16
- ids.tracing: hash-37b96e157a50641d2ba5f4f784cedb09e7c096040827e10bc5dfee5debd28324
- obj.clause-number: Table 16
- obj.element-name: table
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-100000012-d013c582f9b84bd: Product life cycle (use.product-life-cycle) (heading)
- bib.al.original-language: en
- bib.dp.publication-date: 2025-03-01
- ids.document: 99200
- ids.element: o1749224057270-sub-8.3.11
- ids.language-synoptic: o1749224057270-sub-8.3.11
- ids.tracing: hash-a1375bab46b0d5144501df17d8ca4b3bea1b5c9749d67b4dcaa7299ba8fc1fb7
- obj.clause-number: 8.3.11
- obj.element-name: heading
- obj.language: en
- obj.specobject-type: heading
- ChapterName: 8.3.11 Product life cycle (use.product-life-cycle)

##### tr--6d400e6f-d82a-44a1-8922-1185ec080fbf--LxqvLUMP1QnC: Product life cycle (use.product-life-cycle) (provision)
Attribute values see Table 17.
- bib.al.original-language: en
- bib.dp.publication-date: 2025-03-01
- ids.document: 99200
- ids.element: o1749224057270-sub-8.3.11
- ids.language-synoptic: o1749224057270-sub-8.3.11
- ids.tracing: hash-a0b28477f7c3de3b53e1e043a63acebe3f8833a4533755c80e54ac8c81d17bd9
- obj.clause-number: 8.3.11
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-142ff409de434df

##### prov-100000012-142ff409de434df: Values for the attribute use.product-life-cycle (provision)
Table 17 — Values for the attribute use.product-life-cycle
| values | definition |
| --- | --- |
| design | design of a product |
| maintenance | maintenance or service for a product |
| realization | realization of a product |
| recycling | disposal or recycling of a product |
| undefined | default option if required and no value has been provided |
| use phase | use phase for a product |
- bib.al.original-language: en
- bib.dp.publication-date: 2025-03-01
- ids.document: 99200
- ids.element: o1749224057270-tab-17
- ids.language-synoptic: o1749224057270-tab-17
- ids.tracing: hash-5e688d35a97bc38fe5a0dc610ca4876210907c7bead6177116fc170ce2495eee
- obj.clause-number: Table 17
- obj.element-name: table
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-100000012-2d82f4cb0f844c1: Purpose; intention; focus (use.purpose) (heading)
- bib.al.original-language: en
- bib.dp.publication-date: 2025-03-01
- ids.document: 99200
- ids.element: o1749224057272-sub-8.3.12
- ids.language-synoptic: o1749224057272-sub-8.3.12
- ids.tracing: hash-cc9d943e100f78aa78c44dfd7b293ee349f7cc23ba9a4b94c2f1919f95415218
- obj.clause-number: 8.3.12
- obj.element-name: heading
- obj.language: en
- obj.specobject-type: heading
- ChapterName: 8.3.12 Purpose; intention; focus (use.purpose)

##### tr--6d400e6f-d82a-44a1-8922-1185ec080fbf--CsEdIm0knRoR: Purpose; intention; focus (use.purpose) (provision)
Attribute values see Table 18.
- bib.al.original-language: en
- bib.dp.publication-date: 2025-03-01
- ids.document: 99200
- ids.element: o1749224057272-sub-8.3.12
- ids.language-synoptic: o1749224057272-sub-8.3.12
- ids.tracing: hash-2ee466a611101f1c97304b1cdb4e1681e306b49bd8b97cba27976af91caa8a06
- obj.clause-number: 8.3.12
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-7a6dd6a9a3584bd

##### prov-100000012-7a6dd6a9a3584bd: Values for the attribute use.purpose (provision)
Table 18 — Values for the attribute use.purpose
| values | definition |
| --- | --- |
| availability | provision serves availability |
| communication | provision serves communication; means informative |
| future proof | provision serves future-proof |
| health | provision serves health |
| interoperability | interoperability is a separate functionality |
| maintainability | provision serves maintainability |
| quality | provision serves quality |
| relation | provision shows connections, e. g., "Normative references“ |
| reliability | provision serves reliability |
| safety | provision serves safety |
| sustainability | provision serves sustainability |
| undefined | default option if required and no value has been provided |
- bib.al.original-language: en
- bib.dp.publication-date: 2025-03-01
- ids.document: 99200
- ids.element: o1749224057272-tab-18
- ids.language-synoptic: o1749224057272-tab-18
- ids.tracing: hash-791e2d85a90726f038f1aba4142d9cc9270c1773dc3e471bee1d896d3cc7fcb4
- obj.clause-number: Table 18
- obj.element-name: table
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-100000012-e0c5df8513054b8: Long name and identifier syntax (heading)
- bib.al.original-language: en
- bib.dp.publication-date: 2025-03-01
- ids.document: 99200
- ids.element: o1749224057275-sub-8.4
- ids.language-synoptic: o1749224057275-sub-8.4
- ids.tracing: hash-5cad2bdfa4216696555fcdb25ed7a1e9d0c82a4d0da70df59f34577e29992abb
- obj.clause-number: 8.4
- obj.element-name: heading
- obj.language: en
- obj.specobject-type: heading
- ChapterName: 8.4 Long name and identifier syntax

#### prov-100000012-3cffda04d4c8413: Datatype definitions (DataTypeDefinitions) (heading)
- bib.al.original-language: en
- bib.dp.publication-date: 2025-03-01
- ids.document: 99200
- ids.element: o1749224057277-sub-8.4.1
- ids.language-synoptic: o1749224057277-sub-8.4.1
- ids.tracing: hash-7e62e547cf14a8acd4b7dcdad1971ae2361defec454df9286c3a89f362edfd2d
- obj.clause-number: 8.4.1
- obj.element-name: heading
- obj.language: en
- obj.specobject-type: heading
- ChapterName: 8.4.1 Datatype definitions (DataTypeDefinitions)

##### tr--6d400e6f-d82a-44a1-8922-1185ec080fbf--R5RK8nWoCFTy: Datatype definitions (DataTypeDefinitions) (provision)
DataTypeDefinitions see Table 19.
- bib.al.original-language: en
- bib.dp.publication-date: 2025-03-01
- ids.document: 99200
- ids.element: o1749224057277-sub-8.4.1
- ids.language-synoptic: o1749224057277-sub-8.4.1
- ids.tracing: hash-1eccf69deecae17dd2f96dd71e5a94a7a2492c4f51345944464f732c07db614b
- obj.clause-number: 8.4.1
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-09302099dfb2414

##### prov-100000012-09302099dfb2414: DataTypeDefinitions (provision)
Table 19 — DataTypeDefinitions
| long name | identifier | class name | class name abbreviation |
| --- | --- | --- | --- |
| date | tr--ddd--date | DatatypeDefinitionDate | ddd |
| element-name | tr--dde--element-name | DatatypeDefinitionEnumeration | dde |
| block | tr--ev--element-name--block | EnumValue | ev |
| caption | tr--ev--element-name--caption | EnumValue | ev |
| concept | tr--ev--element-name--concept | EnumValue | ev |
| descriptive-list | tr--ev--element-name--descriptive-list | EnumValue | ev |
| display-formula | tr--ev--element-name--display-formula | EnumValue | ev |
| document | tr--ev--element-name--document | EnumValue | ev |
| example | tr--ev--element-name--example | EnumValue | ev |
| figure | tr--ev--element-name--figure | EnumValue | ev |
| footnote | tr--ev--element-name--footnote | EnumValue | ev |
| formula | tr--ev--element-name--formula | EnumValue | ev |
| graphics | tr--ev--element-name--graphics | EnumValue | ev |
| heading | tr--ev--element-name--heading | EnumValue | ev |
| legend | tr--ev--element-name--legend | EnumValue | ev |
| list-of-documents | tr--ev--element-name--list-of-documents | EnumValue | ev |
| note | tr--ev--element-name--note | EnumValue | ev |
| ordered-list | tr--ev--element-name--ordered-list | EnumValue | ev |
| ordering-details | tr--ev--element-name--ordering-details | EnumValue | ev |
| paragraph | tr--ev--element-name--paragraph | EnumValue | ev |
| printed-form | tr--ev--element-name--printed-form | EnumValue | ev |
| profile | tr--ev--element-name--profile | EnumValue | ev |
| quotation | tr--ev--element-name--quotation | EnumValue | ev |
| signature | tr--ev--element-name--signature | EnumValue | ev |
| standard-designation | tr--ev--element-name--standard-designation | EnumValue | ev |
| table | tr--ev--element-name--table | EnumValue | ev |
| tabular-form | tr--ev--element-name--tabular-form | EnumValue | ev |
| typed-form | tr--ev--element-name--typed-form | EnumValue | ev |
| undefined | tr--ev--element-name--undefined | EnumValue | ev |
| units | tr--ev--element-name--units | EnumValue | ev |
| unordered-list | tr--ev--element-name--unordered-list | EnumValue | ev |
| warning | tr--ev--element-name--warning | EnumValue | ev |
| integer | tr--ddi--integer | DatatypeDefinitionInteger | ddi |
| integer-percentage | tr--ddi--integer-percentage | DatatypeDefinitionInteger | ddi |
| language | tr--dde--language | DatatypeDefinitionEnumeration | dde |
| ar | tr--ev--language--ar | EnumValue | ev |
| be | tr--ev--language--be | EnumValue | ev |
| bg | tr--ev--language--bg | EnumValue | ev |
| bs | tr--ev--language--bs | EnumValue | ev |
| cs | tr--ev--language--cs | EnumValue | ev |
| da | tr--ev--language--da | EnumValue | ev |
| de | tr--ev--language--de | EnumValue | ev |
| el | tr--ev--language--el | EnumValue | ev |
| en | tr--ev--language--en | EnumValue | ev |
| es | tr--ev--language--es | EnumValue | ev |
| et | tr--ev--language--et | EnumValue | ev |
| fi | tr--ev--language--fi | EnumValue | ev |
| fr | tr--ev--language--fr | EnumValue | ev |
| ga | tr--ev--language--ga | EnumValue | ev |
| he | tr--ev--language--he | EnumValue | ev |
| hr | tr--ev--language--hr | EnumValue | ev |
| hu | tr--ev--language--hu | EnumValue | ev |
| id | tr--ev--language--id | EnumValue | ev |
| is | tr--ev--language--is | EnumValue | ev |
| it | tr--ev--language--it | EnumValue | ev |
| ja | tr--ev--language--ja | EnumValue | ev |
| ka | tr--ev--language--ka | EnumValue | ev |
| ko | tr--ev--language--ko | EnumValue | ev |
| lb | tr--ev--language--lb | EnumValue | ev |
| lt | tr--ev--language--lt | EnumValue | ev |
| lv | tr--ev--language--lv | EnumValue | ev |
| mk | tr--ev--language--mk | EnumValue | ev |
| mt | tr--ev--language--mt | EnumValue | ev |
| nl | tr--ev--language--nl | EnumValue | ev |
| no | tr--ev--language--no | EnumValue | ev |
| pl | tr--ev--language--pl | EnumValue | ev |
| pt | tr--ev--language--pt | EnumValue | ev |
| ro | tr--ev--language--ro | EnumValue | ev |
| ru | tr--ev--language--ru | EnumValue | ev |
| sk | tr--ev--language--sk | EnumValue | ev |
| sl | tr--ev--language--sl | EnumValue | ev |
| sq | tr--ev--language--sq | EnumValue | ev |
| sr | tr--ev--language--sr | EnumValue | ev |
| sv | tr--ev--language--sv | EnumValue | ev |
| tr | tr--ev--language--tr | EnumValue | ev |
| uk | tr--ev--language--uk | EnumValue | ev |
| undefined | tr--ev--language--undefined | EnumValue | ev |
| vi | tr--ev--language--vi | EnumValue | ev |
| zh | tr--ev--language--zh | EnumValue | ev |
| modality | tr--dde--modality | DatatypeDefinitionEnumeration | dde |
| ambiguous | tr--ev--modality--ambiguous | EnumValue | ev |
| capability | tr--ev--modality--capability | EnumValue | ev |
| constraint | tr--ev--modality--constraint | EnumValue | ev |
| permission | tr--ev--modality--permission | EnumValue | ev |
| possibility | tr--ev--modality--possibility | EnumValue | ev |
| recommendation | tr--ev--modality--recommendation | EnumValue | ev |
| requirement | tr--ev--modality--requirement | EnumValue | ev |
| undefined | tr--ev--modality--undefined | EnumValue | ev |
| normativity | tr--dde--normativity | DatatypeDefinitionEnumeration | dde |
| informative | tr--ev--normativity--informative | EnumValue | ev |
| normative | tr--ev--normativity--normative | EnumValue | ev |
| undefined | tr--ev--normativity--undefined | EnumValue | ev |
| specobject-type | tr--dde--specobject-type | DatatypeDefinitionEnumeration | dde |
| document | tr--ev--specobject-type--document | EnumValue | ev |
| heading | tr--ev--specobject-type--heading | EnumValue | ev |
| provision | tr--ev--specobject-type--provision | EnumValue | ev |
| undefined | tr--ev--specobject-type--undefined | EnumValue | ev |
| string-1024 | tr--dds--string-1024 | DatatypeDefinitionString | dds |
| string-16384 | tr--dds--string-16384 | DatatypeDefinitionString | dds |
| string-64 | tr--dds--string-64 | DatatypeDefinitionString | dds |
| string-date | tr--dds--string-date | DatatypeDefinitionString | dds |
| use.business-process | tr--dde--use.business-process | DatatypeDefinitionEnumeration | dde |
| logistics external | tr--ev--use.business-process--logistics-external | EnumValue | ev |
| logistics internal | tr--ev--use.business-process--logistics-internal | EnumValue | ev |
| marketing and sales | tr--ev--use.business-process--marketing-and-sales | EnumValue | ev |
| production | tr--ev--use.business-process--production | EnumValue | ev |
| service | tr--ev--use.business-process--service | EnumValue | ev |
| supporting – acquisition | tr--ev--use.business-process--supporting---acquisition | EnumValue | ev |
| supporting – corporate infrastructure | tr--ev--use.business-process--supporting---corporate-infrastructure | EnumValue | ev |
| supporting – human resource management | tr--ev--use.business-process--supporting---human-resource-management | EnumValue | ev |
| supporting – technology development | tr--ev--use.business-process--supporting---technology-development | EnumValue | ev |
| undefined | tr--ev--use.business-process--undefined | EnumValue | ev |
| use.business-sector | tr--dde--use.business-sector | DatatypeDefinitionEnumeration | dde |
| building | tr--ev--use.business-sector--building | EnumValue | ev |
| consumer discretionary | tr--ev--use.business-sector--consumer-discretionary | EnumValue | ev |
| consumer services | tr--ev--use.business-sector--consumer-services | EnumValue | ev |
| consumer staples | tr--ev--use.business-sector--consumer-staples | EnumValue | ev |
| energy | tr--ev--use.business-sector--energy | EnumValue | ev |
| financials | tr--ev--use.business-sector--financials | EnumValue | ev |
| healthcare | tr--ev--use.business-sector--healthcare | EnumValue | ev |
| industrials – aerospace | tr--ev--use.business-sector--industrials---aerospace | EnumValue | ev |
| industrials – automotive | tr--ev--use.business-sector--industrials---automotive | EnumValue | ev |
| industrials – defense | tr--ev--use.business-sector--industrials---defense | EnumValue | ev |
| industrials – electrical engineering | tr--ev--use.business-sector--industrials---electrical-engineering | EnumValue | ev |
| industrials – mechanical engineering | tr--ev--use.business-sector--industrials---mechanical-engineering | EnumValue | ev |
| industrials – medical engineering | tr--ev--use.business-sector--industrials---medical-engineering | EnumValue | ev |
| materials | tr--ev--use.business-sector--materials | EnumValue | ev |
| other | tr--ev--use.business-sector--other | EnumValue | ev |
| real estate | tr--ev--use.business-sector--real-estate | EnumValue | ev |
| services | tr--ev--use.business-sector--services | EnumValue | ev |
| technology | tr--ev--use.business-sector--technology | EnumValue | ev |
| undefined | tr--ev--use.business-sector--undefined | EnumValue | ev |
| utilities | tr--ev--use.business-sector--utilities | EnumValue | ev |
| use.interaction | tr--dde--use.interaction | DatatypeDefinitionEnumeration | dde |
| activity | tr--ev--use.interaction--activity | EnumValue | ev |
| functional | tr--ev--use.interaction--functional | EnumValue | ev |
| integral aspect | tr--ev--use.interaction--integral-aspect | EnumValue | ev |
| interface | tr--ev--use.interaction--interface | EnumValue | ev |
| undefined | tr--ev--use.interaction--undefined | EnumValue | ev |
| verification | tr--ev--use.interaction--verification | EnumValue | ev |
| use.location | tr--dde--use.location | DatatypeDefinitionEnumeration | dde |
| abb | tr--ev--use.location--abb | EnumValue | ev |
| alb | tr--ev--use.location--alb | EnumValue | ev |
| and | tr--ev--use.location--and | EnumValue | ev |
| atg | tr--ev--use.location--atg | EnumValue | ev |
| aus | tr--ev--use.location--aus | EnumValue | ev |
| aut | tr--ev--use.location--aut | EnumValue | ev |
| bel | tr--ev--use.location--bel | EnumValue | ev |
| bgr | tr--ev--use.location--bgr | EnumValue | ev |
| bhs | tr--ev--use.location--bhs | EnumValue | ev |
| bih | tr--ev--use.location--bih | EnumValue | ev |
| blr | tr--ev--use.location--blr | EnumValue | ev |
| can | tr--ev--use.location--can | EnumValue | ev |
| che | tr--ev--use.location--che | EnumValue | ev |
| chn | tr--ev--use.location--chn | EnumValue | ev |
| cub | tr--ev--use.location--cub | EnumValue | ev |
| cyp | tr--ev--use.location--cyp | EnumValue | ev |
| cze | tr--ev--use.location--cze | EnumValue | ev |
| deu | tr--ev--use.location--deu | EnumValue | ev |
| dnk | tr--ev--use.location--dnk | EnumValue | ev |
| eee | tr--ev--use.location--eee | EnumValue | ev |
| esp | tr--ev--use.location--esp | EnumValue | ev |
| est | tr--ev--use.location--est | EnumValue | ev |
| fff | tr--ev--use.location--fff | EnumValue | ev |
| fin | tr--ev--use.location--fin | EnumValue | ev |
| fra | tr--ev--use.location--fra | EnumValue | ev |
| gbr | tr--ev--use.location--gbr | EnumValue | ev |
| geo | tr--ev--use.location--geo | EnumValue | ev |
| gib | tr--ev--use.location--gib | EnumValue | ev |
| grc | tr--ev--use.location--grc | EnumValue | ev |
| hkg | tr--ev--use.location--hkg | EnumValue | ev |
| hrv | tr--ev--use.location--hrv | EnumValue | ev |
| hun | tr--ev--use.location--hun | EnumValue | ev |
| idn | tr--ev--use.location--idn | EnumValue | ev |
| ind | tr--ev--use.location--ind | EnumValue | ev |
| irl | tr--ev--use.location--irl | EnumValue | ev |
| isl | tr--ev--use.location--isl | EnumValue | ev |
| isr | tr--ev--use.location--isr | EnumValue | ev |
| ita | tr--ev--use.location--ita | EnumValue | ev |
| jam | tr--ev--use.location--jam | EnumValue | ev |
| jpn | tr--ev--use.location--jpn | EnumValue | ev |
| kgz | tr--ev--use.location--kgz | EnumValue | ev |
| kor | tr--ev--use.location--kor | EnumValue | ev |
| kos | tr--ev--use.location--kos | EnumValue | ev |
| kwt | tr--ev--use.location--kwt | EnumValue | ev |
| lie | tr--ev--use.location--lie | EnumValue | ev |
| ltu | tr--ev--use.location--ltu | EnumValue | ev |
| lux | tr--ev--use.location--lux | EnumValue | ev |
| lva | tr--ev--use.location--lva | EnumValue | ev |
| mco | tr--ev--use.location--mco | EnumValue | ev |
| mda | tr--ev--use.location--mda | EnumValue | ev |
| mkd | tr--ev--use.location--mkd | EnumValue | ev |
| mlt | tr--ev--use.location--mlt | EnumValue | ev |
| mne | tr--ev--use.location--mne | EnumValue | ev |
| nld | tr--ev--use.location--nld | EnumValue | ev |
| nnn | tr--ev--use.location--nnn | EnumValue | ev |
| nor | tr--ev--use.location--nor | EnumValue | ev |
| nzl | tr--ev--use.location--nzl | EnumValue | ev |
| phl | tr--ev--use.location--phl | EnumValue | ev |
| pol | tr--ev--use.location--pol | EnumValue | ev |
| prk | tr--ev--use.location--prk | EnumValue | ev |
| prt | tr--ev--use.location--prt | EnumValue | ev |
| rou | tr--ev--use.location--rou | EnumValue | ev |
| rus | tr--ev--use.location--rus | EnumValue | ev |
| sau | tr--ev--use.location--sau | EnumValue | ev |
| srb | tr--ev--use.location--srb | EnumValue | ev |
| svk | tr--ev--use.location--svk | EnumValue | ev |
| srr | tr--ev--use.location--srr | EnumValue | ev |
| svn | tr--ev--use.location--svn | EnumValue | ev |
| swe | tr--ev--use.location--swe | EnumValue | ev |
| tjk | tr--ev--use.location--tjk | EnumValue | ev |
| tur | tr--ev--use.location--tur | EnumValue | ev |
| twn | tr--ev--use.location--twn | EnumValue | ev |
| ukr | tr--ev--use.location--ukr | EnumValue | ev |
| undefined | tr--ev--use.location--undefined | EnumValue | ev |
| usa | tr--ev--use.location--usa | EnumValue | ev |
| vnm | tr--ev--use.location--vnm | EnumValue | ev |
| use.product-life-cycle | tr--dde--use.product-life-cycle | DatatypeDefinitionEnumeration | dde |
| design | tr--ev--use.product-life-cycle--design | EnumValue | ev |
| maintenance | tr--ev--use.product-life-cycle--maintenance | EnumValue | ev |
| realization | tr--ev--use.product-life-cycle--realization | EnumValue | ev |
| recycling | tr--ev--use.product-life-cycle--recycling | EnumValue | ev |
| undefined | tr--ev--use.product-life-cycle--undefined | EnumValue | ev |
| use phase | tr--ev--use.product-life-cycle--use-phase | EnumValue | ev |
| use.project-phase | tr--dde--use.project-phase | DatatypeDefinitionEnumeration | dde |
| close out | tr--ev--use.project-phase--close-out | EnumValue | ev |
| definition and planning | tr--ev--use.project-phase--definition-and-planning | EnumValue | ev |
| execution | tr--ev--use.project-phase--execution | EnumValue | ev |
| initiation | tr--ev--use.project-phase--initiation | EnumValue | ev |
| monitoring and control | tr--ev--use.project-phase--monitoring-and-control | EnumValue | ev |
| undefined | tr--ev--use.project-phase--undefined | EnumValue | ev |
| use.purpose | tr--dde--use.purpose | DatatypeDefinitionEnumeration | dde |
| availability | tr--ev--use.purpose--availability | EnumValue | ev |
| communication | tr--ev--use.purpose--communication | EnumValue | ev |
| future proof | tr--ev--use.purpose--future-proof | EnumValue | ev |
| health | tr--ev--use.purpose--health | EnumValue | ev |
| interoperability | tr--ev--use.purpose--interoperability | EnumValue | ev |
| maintainability | tr--ev--use.purpose--maintainability | EnumValue | ev |
| quality | tr--ev--use.purpose--quality | EnumValue | ev |
| relation | tr--ev--use.purpose--relation | EnumValue | ev |
| reliability | tr--ev--use.purpose--reliability | EnumValue | ev |
| safety | tr--ev--use.purpose--safety | EnumValue | ev |
| sustainablility | tr--ev--use.purpose--sustainablility | EnumValue | ev |
| undefined | tr--ev--use.purpose--undefined | EnumValue | ev |
| xhtml | tr--ddx--xhtml | DatatypeDefinitionXHTML | ddx |
- bib.al.original-language: en
- bib.dp.publication-date: 2025-03-01
- ids.document: 99200
- ids.element: o1749224057277-tab-19
- ids.language-synoptic: o1749224057277-tab-19
- ids.tracing: hash-f6a2a76c7491b2e695cda504e3c9ea6a59f7ac0e461d4951a6f016aeab70bfbe
- obj.clause-number: Table 19
- obj.element-name: table
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-100000012-88bef5bd002b421: Specification types (SpecTypes) (heading)
- bib.al.original-language: en
- bib.dp.publication-date: 2025-03-01
- ids.document: 99200
- ids.element: o1749224057280-sub-8.4.2
- ids.language-synoptic: o1749224057280-sub-8.4.2
- ids.tracing: hash-88e08a40e052cd49277b8b72fab8b75dc7387293df7b7c12e9998268853cbc42
- obj.clause-number: 8.4.2
- obj.element-name: heading
- obj.language: en
- obj.specobject-type: heading
- ChapterName: 8.4.2 Specification types (SpecTypes)

##### prov-100000012-0543b5f7ecb3466: Relation group types (RelationGroupTypes) (heading)
- bib.al.original-language: en
- bib.dp.publication-date: 2025-03-01
- ids.document: 99200
- ids.element: o1749224057282-sub-8.4.2.1
- ids.language-synoptic: o1749224057282-sub-8.4.2.1
- ids.tracing: hash-f1c68dbd03dc7c83b3e0f3859d68a57993b918dc53f29bbd0202f5c708e0be35
- obj.clause-number: 8.4.2.1
- obj.element-name: heading
- obj.language: en
- obj.specobject-type: heading
- ChapterName: 8.4.2.1 Relation group types (RelationGroupTypes)

###### tr--6d400e6f-d82a-44a1-8922-1185ec080fbf--a7ymSfln9TmD: Relation group types (RelationGroupTypes) (provision)
RelationGroupTypes see Table 20.
- bib.al.original-language: en
- bib.dp.publication-date: 2025-03-01
- ids.document: 99200
- ids.element: o1749224057282-sub-8.4.2.1
- ids.language-synoptic: o1749224057282-sub-8.4.2.1
- ids.tracing: hash-a089603403b2e3a4884dcb9a8e8e5ee587824dc7dde7d5074058c5accdb57715
- obj.clause-number: 8.4.2.1
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-290218bddbce46c

###### prov-100000012-290218bddbce46c: RelationGroupTypes (provision)
Table 20 — RelationGroupTypes
| long name | identifier | class name | class name abbreviation |
| --- | --- | --- | --- |
| relation-group-standard | tr--rgt--relation-group-standard | RelationGroupType | rgt |
| relation-group-external | tr--rg--relation-group-standard--relation-group-external | RelationGroup | rg |
| relation-group-internal | tr--rg--relation-group-standard--relation-group-internal | RelationGroup | rg |
- bib.al.original-language: en
- bib.dp.publication-date: 2025-03-01
- ids.document: 99200
- ids.element: o1749224057282-tab-20
- ids.language-synoptic: o1749224057282-tab-20
- ids.tracing: hash-a04aedccd0b6358877842961f88a1d43e52fbe838294f4b8b67a7d2ca967e1a1
- obj.clause-number: Table 20
- obj.element-name: table
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-fab750cdc54a4b9: Specification types (SpecificationTypes) (heading)
- bib.al.original-language: en
- bib.dp.publication-date: 2025-03-01
- ids.document: 99200
- ids.element: o1749224057284-sub-8.4.2.2
- ids.language-synoptic: o1749224057284-sub-8.4.2.2
- ids.tracing: hash-515594b48b16b0e0cfcf2c1291880e837c7db453e6189320ee157607361d8e1d
- obj.clause-number: 8.4.2.2
- obj.element-name: heading
- obj.language: en
- obj.specobject-type: heading
- ChapterName: 8.4.2.2 Specification types (SpecificationTypes)

###### tr--6d400e6f-d82a-44a1-8922-1185ec080fbf--vpxHW0MAi9PW: Specification types (SpecificationTypes) (provision)
SpecificationTypes see Table 21.
- bib.al.original-language: en
- bib.dp.publication-date: 2025-03-01
- ids.document: 99200
- ids.element: o1749224057284-sub-8.4.2.2
- ids.language-synoptic: o1749224057284-sub-8.4.2.2
- ids.tracing: hash-b30a88de2df925d854198221b26046eef450c06a265110b9662dc59a43576c09
- obj.clause-number: 8.4.2.2
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-0dc3dc5a35014a8

###### prov-100000012-0dc3dc5a35014a8: SpecificationTypes (provision)
Table 21 — SpecificationTypes
| long name | identifier | class name | class name abbreviation |
| --- | --- | --- | --- |
| specification-standard | tr--st--specification-standard | SpecificationType | st |
| bib.al.original-language | tr--ads--specification-standard--bib.al.original-language | AttributeDefinitionString | ads |
| bib.as.amends | tr--ads--specification-standard--bib.as.amends | AttributeDefinitionString | ads |
| bib.az.amended-by | tr--ads--specification-standard--bib.az.amended-by | AttributeDefinitionString | ads |
| bib.ca.classification | tr--ads--specification-standard--bib.ca.classification | AttributeDefinitionString | ads |
| bib.ct.descriptors-german | tr--ads--specification-standard--bib.ct.descriptors-german | AttributeDefinitionString | ads |
| bib.di.document-identifier | tr--ads--specification-standard--bib.di.document-identifier | AttributeDefinitionString | ads |
| bib.dp.publication-date | tr--ads--specification-standard--bib.dp.publication-date | AttributeDefinitionString | ads |
| bib.et.descriptors-english | tr--ads--specification-standard--bib.et.descriptors-english | AttributeDefinitionString | ads |
| bib.ft.descriptors-french | tr--ads--specification-standard--bib.ft.descriptors-french | AttributeDefinitionString | ads |
| bib.ii.international-relationship | tr--ads--specification-standard--bib.ii.international-relationship | AttributeDefinitionString | ads |
| bib.rx.replaced-by | tr--ads--specification-standard--bib.rx.replaced-by | AttributeDefinitionString | ads |
| bib.rz.replaces | tr--ads--specification-standard--bib.rz.replaces | AttributeDefinitionString | ads |
| bib.tf.title-french | tr--adx--specification-standard--bib.tf.title-french | AttributeDefinitionXHTML | adx |
| bib.tg.title-german | tr--adx--specification-standard--bib.tg.title-german | AttributeDefinitionXHTML | adx |
| bib.ti.title-english | tr--adx--specification-standard--bib.ti.title-english | AttributeDefinitionXHTML | adx |
| bib.ts.document-type | tr--ads--specification-standard--bib.ts.document-type | AttributeDefinitionString | ads |
| bib.up.update-flag | tr--ads--specification-standard--bib.up.update-flag | AttributeDefinitionString | ads |
| obj.transformation-issues | tr--ads--specification-standard--obj.transformation-issues | AttributeDefinitionString | ads |
- bib.al.original-language: en
- bib.dp.publication-date: 2025-03-01
- ids.document: 99200
- ids.element: o1749224057284-tab-21
- ids.language-synoptic: o1749224057284-tab-21
- ids.tracing: hash-d83b8d98b5804ee861105f44aa982b927a1b542bd89b01467b57211c98be9dcd
- obj.clause-number: Table 21
- obj.element-name: table
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-9260ee5a27bc49a: Specification object types (SpecObjectTypes) (heading)
- bib.al.original-language: en
- bib.dp.publication-date: 2025-03-01
- ids.document: 99200
- ids.element: o1749224057286-sub-8.4.2.3
- ids.language-synoptic: o1749224057286-sub-8.4.2.3
- ids.tracing: hash-a24e846980d6331f0cfac282edb9a9c875b140700c7e992ad1fdb250c8d9eaa0
- obj.clause-number: 8.4.2.3
- obj.element-name: heading
- obj.language: en
- obj.specobject-type: heading
- ChapterName: 8.4.2.3 Specification object types (SpecObjectTypes)

###### tr--6d400e6f-d82a-44a1-8922-1185ec080fbf--UMG6c1bWSKq8: Specification object types (SpecObjectTypes) (provision)
SpecObjectTypes see Table 22.
- bib.al.original-language: en
- bib.dp.publication-date: 2025-03-01
- ids.document: 99200
- ids.element: o1749224057286-sub-8.4.2.3
- ids.language-synoptic: o1749224057286-sub-8.4.2.3
- ids.tracing: hash-a064a3283d2eabd840856e20aae4620159c514d8659de9e76a475ec567797e5c
- obj.clause-number: 8.4.2.3
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-f67952635848434

###### prov-100000012-f67952635848434: SpecObjectTypes (provision)
Table 22 — SpecObjectTypes
| long name | identifier | class name | class name abbreviation |
| --- | --- | --- | --- |
| document | tr--sot--document | SpecObjectType | sot |
| bib.al.original-language | tr--ads--document--bib.al.original-language | AttributeDefinitionString | ads |
| bib.as.amends | tr--ads--document--bib.as.amends | AttributeDefinitionString | ads |
| bib.az.amended-by | tr--ads--document--bib.az.amended-by | AttributeDefinitionString | ads |
| bib.ca.classification | tr--ads--document--bib.ca.classification | AttributeDefinitionString | ads |
| bib.ct.descriptors-german | tr--ads--document--bib.ct.descriptors-german | AttributeDefinitionString | ads |
| bib.di.document-identifier | tr--ads--document--bib.di.document-identifier | AttributeDefinitionString | ads |
| bib.dp.publication-date | tr--ads--document--bib.dp.publication-date | AttributeDefinitionString | ads |
| bib.et.descriptors-english | tr--ads--document--bib.et.descriptors-english | AttributeDefinitionString | ads |
| bib.ft.descriptors-french | tr--ads--document--bib.ft.descriptors-french | AttributeDefinitionString | ads |
| bib.ii.international-relationship | tr--ads--document--bib.ii.international-relationship | AttributeDefinitionString | ads |
| bib.rx.replaced-by | tr--ads--document--bib.rx.replaced-by | AttributeDefinitionString | ads |
| bib.rz.replaces | tr--ads--document--bib.rz.replaces | AttributeDefinitionString | ads |
| bib.tf.title-french | tr--adx--document--bib.tf.title-french | AttributeDefinitionXHTML | adx |
| bib.tg.title-german | tr--adx--document--bib.tg.title-german | AttributeDefinitionXHTML | adx |
| bib.ti.title-english | tr--adx--document--bib.ti.title-english | AttributeDefinitionXHTML | adx |
| bib.ts.document-type | tr--ads--document--bib.ts.document-type | AttributeDefinitionString | ads |
| bib.up.update-flag | tr--ads--document--bib.up.update-flag | AttributeDefinitionString | ads |
| ids.document | tr--ads--document--ids.document | AttributeDefinitionString | ads |
| obj.language | tr--ade--document--obj.language | AttributeDefinitionEnumeration | ade |
| obj.specobject-type | tr--ade--document--obj.specobject-type | AttributeDefinitionEnumeration | ade |
| obj.transformation-issues | tr--ads--document--obj.transformation-issues | AttributeDefinitionString | ads |
| pub.harmonization | tr--ads--document--pub.harmonization | AttributeDefinitionString | ads |
| pub.originator | tr--ads--document--pub.originator | AttributeDefinitionString | ads |
| pub.software | tr--ads--document--pub.software | AttributeDefinitionString | ads |
| pub.supplier | tr--ads--document--pub.supplier | AttributeDefinitionString | ads |
| ReqIF.Text | tr--adx--document--reqif.text | AttributeDefinitionXHTML | adx |
| heading | tr--sot--heading | SpecObjectType | sot |
| bib.di.document-identifier | tr--ads--heading--bib.di.document-identifier | AttributeDefinitionString | ads |
| bib.dp.publication-date | tr--ads--heading--bib.dp.publication-date | AttributeDefinitionString | ads |
| ids.document | tr--ads--heading--ids.document | AttributeDefinitionString | ads |
| ids.element | tr--ads--heading--ids.element | AttributeDefinitionString | ads |
| ids.tracing | tr--ads--heading--ids.tracing | AttributeDefinitionString | ads |
| ids.unique | tr--ads--heading--ids.unique | AttributeDefinitionString | ads |
| obj.clause-heading | tr--ads--heading--obj.clause-heading | AttributeDefinitionString | ads |
| obj.clause-number | tr--ads--heading--obj.clause-number | AttributeDefinitionString | ads |
| obj.element-name | tr--ade--heading--obj.element-name | AttributeDefinitionEnumeration | ade |
| obj.language | tr--ade--heading--obj.language | AttributeDefinitionEnumeration | ade |
| obj.specobject-type | tr--ade--heading--obj.specobject-type | AttributeDefinitionEnumeration | ade |
| obj.transformation-issues | tr--ads--heading--obj.transformation-issues | AttributeDefinitionString | ads |
| ReqIF.ChapterName | tr--adx--heading--reqif.chaptername | AttributeDefinitionXHTML | adx |
| provision | tr--sot--provision | SpecObjectType | sot |
| bib.al.original-language | tr--ads--provision--bib.al.original-language | AttributeDefinitionString | ads |
| bib.as.amends | tr--ads--provision--bib.as.amends | AttributeDefinitionString | ads |
| bib.az.amended-by | tr--ads--provision--bib.az.amended-by | AttributeDefinitionString | ads |
| bib.ca.classification | tr--ads--provision--bib.ca.classification | AttributeDefinitionString | ads |
| bib.ct.descriptors-german | tr--ads--provision--bib.ct.descriptors-german | AttributeDefinitionString | ads |
| bib.di.document-identifier | tr--ads--provision--bib.di.document-identifier | AttributeDefinitionString | ads |
| bib.dp.publication-date | tr--ads--provision--bib.dp.publication-date | AttributeDefinitionString | ads |
| bib.et.descriptors-english | tr--ads--provision--bib.et.descriptors-english | AttributeDefinitionString | ads |
| bib.ft.descriptors-french | tr--ads--provision--bib.ft.descriptors-french | AttributeDefinitionString | ads |
| bib.ii.international-relationship | tr--ads--provision--bib.ii.international-relationship | AttributeDefinitionString | ads |
| bib.rx.replaced-by | tr--ads--provision--bib.rx.replaced-by | AttributeDefinitionString | ads |
| bib.rz.replaces | tr--ads--provision--bib.rz.replaces | AttributeDefinitionString | ads |
| bib.tf.title-french | tr--adx--provision--bib.tf.title-french | AttributeDefinitionXHTML | adx |
| bib.tg.title-german | tr--adx--provision--bib.tg.title-german | AttributeDefinitionXHTML | adx |
| bib.ti.title-english | tr--adx--provision--bib.ti.title-english | AttributeDefinitionXHTML | adx |
| bib.ts.document-type | tr--ads--provision--bib.ts.document-type | AttributeDefinitionString | ads |
| bib.up.update-flag | tr--ads--provision--bib.up.update-flag | AttributeDefinitionString | ads |
| ids.document | tr--ads--provision--ids.document | AttributeDefinitionString | ads |
| ids.element | tr--ads--provision--ids.element | AttributeDefinitionString | ads |
| ids.tracing | tr--ads--provision--ids.tracing | AttributeDefinitionString | ads |
| ids.unique | tr--ads--provision--ids.unique | AttributeDefinitionString | ads |
| ids.xpath-end | tr--ads--provision--ids.xpath-end | AttributeDefinitionString | ads |
| ids.xpath-start | tr--ads--provision--ids.xpath-start | AttributeDefinitionString | ads |
| obj.clause-heading | tr--ads--provision--obj.clause-heading | AttributeDefinitionString | ads |
| obj.clause-number | tr--ads--provision--obj.clause-number | AttributeDefinitionString | ads |
| obj.conversion-reliability | tr--adi--provision--obj.conversion-reliability | AttributeDefinitionInteger | adi |
| obj.element-name | tr--ade--provision--obj.element-name | AttributeDefinitionEnumeration | ade |
| obj.language | tr--ade--provision--obj.language | AttributeDefinitionEnumeration | ade |
| obj.modality | tr--ade--provision--obj.modality | AttributeDefinitionEnumeration | ade |
| obj.normativity | tr--ade--provision--obj.normativity | AttributeDefinitionEnumeration | ade |
| obj.specobject-type | tr--ade--provision--obj.specobject-type | AttributeDefinitionEnumeration | ade |
| obj.transformation-issues | tr--ads--provision--obj.transformation-issues | AttributeDefinitionString | ads |
| ReqIF.Text | tr--adx--provision--reqif.text | AttributeDefinitionXHTML | adx |
| use.business-process | tr--ade--provision--use.business-process | AttributeDefinitionEnumeration | ade |
| use.business-sector | tr--ade--provision--use.business-sector | AttributeDefinitionEnumeration | ade |
| use.date-usage-begins | tr--ads--provision--use.date-usage-begins | AttributeDefinitionString | ads |
| use.date-usage-ends | tr--ads--provision--use.date-usage-ends | AttributeDefinitionString | ads |
| use.interaction | tr--ade--provision--use.interaction | AttributeDefinitionEnumeration | ade |
| use.location | tr--ade--provision--use.location | AttributeDefinitionEnumeration | ade |
| use.product-category | tr--ads--provision--use.product-category | AttributeDefinitionString | ads |
| use.product-life-cycle | tr--ade--provision--use.product-life-cycle | AttributeDefinitionEnumeration | ade |
| use.project-phase | tr--ade--provision--use.project-phase | AttributeDefinitionEnumeration | ade |
| use.purpose | tr--ade--provision--use.purpose | AttributeDefinitionEnumeration | ade |
- bib.al.original-language: en
- bib.dp.publication-date: 2025-03-01
- ids.document: 99200
- ids.element: o1749224057286-tab-22
- ids.language-synoptic: o1749224057286-tab-22
- ids.tracing: hash-58b5fddbf1371eb3067eed95dd3860b90269c72af88c91d382fc2ddaa67f8a97
- obj.clause-number: Table 22
- obj.element-name: table
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-ef8b35dea21d4e8: Specification relation types (SpecRelationTypes) (heading)
- bib.al.original-language: en
- bib.dp.publication-date: 2025-03-01
- ids.document: 99200
- ids.element: o1749224057288-sub-8.4.2.4
- ids.language-synoptic: o1749224057288-sub-8.4.2.4
- ids.tracing: hash-5b68a7e238d2f83ed101b70369b74b770c67a7c8bb1ab80d0862ed0c8b2c4e98
- obj.clause-number: 8.4.2.4
- obj.element-name: heading
- obj.language: en
- obj.specobject-type: heading
- ChapterName: 8.4.2.4 Specification relation types (SpecRelationTypes)

###### tr--6d400e6f-d82a-44a1-8922-1185ec080fbf--n7SnH0KjPgTJ: Specification relation types (SpecRelationTypes) (provision)
SpecRelationTypes see Table 23.
- bib.al.original-language: en
- bib.dp.publication-date: 2025-03-01
- ids.document: 99200
- ids.element: o1749224057288-sub-8.4.2.4
- ids.language-synoptic: o1749224057288-sub-8.4.2.4
- ids.tracing: hash-d2ab2284b472d8ed38aaa5a9100dcb15bb79f57f12ff01914da03c48a5a6666c
- obj.clause-number: 8.4.2.4
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-0e2f5a3db192406

###### prov-100000012-0e2f5a3db192406: SpecRelationTypes (provision)
Table 23 — SpecRelationTypes
| long name | identifier | class name | class name abbreviation |
| --- | --- | --- | --- |
| cross-reference | tr--srt--cross-reference | SpecRelationTypes | srt |
- bib.al.original-language: en
- bib.dp.publication-date: 2025-03-01
- ids.document: 99200
- ids.element: o1749224057288-tab-23
- ids.language-synoptic: o1749224057288-tab-23
- ids.tracing: hash-840db0f9a28d542569330ec8077276e69774adba782604e59a413efdc617fdea
- obj.clause-number: Table 23
- obj.element-name: table
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-100000012-0a2840367a5c487: Specifications (heading)
- bib.al.original-language: en
- bib.dp.publication-date: 2025-03-01
- ids.document: 99200
- ids.element: o1749224057290-sub-8.4.3
- ids.language-synoptic: o1749224057290-sub-8.4.3
- ids.tracing: hash-4d1b09307bd1b3cc11350809b7f5ed75a4fee57762a188a1c2b8331ddea03cf2
- obj.clause-number: 8.4.3
- obj.element-name: heading
- obj.language: en
- obj.specobject-type: heading
- ChapterName: 8.4.3 Specifications

##### tr--6d400e6f-d82a-44a1-8922-1185ec080fbf--BV5huClohEh9: Specifications (provision)
The Specifications contain linkage to the SpecObject content elements.
- bib.al.original-language: en
- bib.dp.publication-date: 2025-03-01
- ids.document: 99200
- ids.element: o1749224057290-sub-8.4.3
- ids.language-synoptic: o1749224057290-sub-8.4.3
- ids.tracing: hash-a678e4efdfeadace778d603af73d1ab8f3cbd34044e6c33944eb8f576eb3eb44
- obj.clause-number: 8.4.3
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-100000012-9b0a6f779a8746d: Specifications Objects (SpecObjects) (heading)
- bib.al.original-language: en
- bib.dp.publication-date: 2025-03-01
- ids.document: 99200
- ids.element: o1749224057292-sub-8.4.4
- ids.language-synoptic: o1749224057292-sub-8.4.4
- ids.tracing: hash-dbef558e17406712a89d7d50ae56d75ad6bd9d3080143e79aeaadef149cdac4b
- obj.clause-number: 8.4.4
- obj.element-name: heading
- obj.language: en
- obj.specobject-type: heading
- ChapterName: 8.4.4 Specifications Objects (SpecObjects)

##### tr--6d400e6f-d82a-44a1-8922-1185ec080fbf--TmBtVrFoUYXW: Specifications Objects (SpecObjects) (provision)
The SpecObjects contain the unsorted collection of all content objects of the document.
- bib.al.original-language: en
- bib.dp.publication-date: 2025-03-01
- ids.document: 99200
- ids.element: o1749224057292-sub-8.4.4
- ids.language-synoptic: o1749224057292-sub-8.4.4
- ids.tracing: hash-7d03e3faead95d54bac16b4f9f468cd765f487df48e8e388f7ff923296731206
- obj.clause-number: 8.4.4
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-100000012-91c3cc57c9654e5: Specification relations (SpecRelations) (heading)
- bib.al.original-language: en
- bib.dp.publication-date: 2025-03-01
- ids.document: 99200
- ids.element: o1749224057294-sub-8.4.5
- ids.language-synoptic: o1749224057294-sub-8.4.5
- ids.tracing: hash-6e3106232f43adbfd0c85c65638e926ddd18ed222d293c1fb3fbee90363e58d4
- obj.clause-number: 8.4.5
- obj.element-name: heading
- obj.language: en
- obj.specobject-type: heading
- ChapterName: 8.4.5 Specification relations (SpecRelations)

##### tr--6d400e6f-d82a-44a1-8922-1185ec080fbf--wbaXhmkB29f0: Specification relations (SpecRelations) (provision)
The SpecRelations contain a collection of all relations between the SpecObjects.
- bib.al.original-language: en
- bib.dp.publication-date: 2025-03-01
- ids.document: 99200
- ids.element: o1749224057294-sub-8.4.5
- ids.language-synoptic: o1749224057294-sub-8.4.5
- ids.tracing: hash-aaa83e315b1620b19e2145e4e795671f1553c7f1070b5e89da2b865c8f4e7ac4
- obj.clause-number: 8.4.5
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-100000012-3b7ba39c5cfb4b0: Specification relation groups (SpecRelationGroups) (heading)
- bib.al.original-language: en
- bib.dp.publication-date: 2025-03-01
- ids.document: 99200
- ids.element: o1749224057296-sub-8.4.6
- ids.language-synoptic: o1749224057296-sub-8.4.6
- ids.tracing: hash-373a5c8617eab841aae2eabcfe714301f61e3c27ea0cd806fe98b1603059ee6e
- obj.clause-number: 8.4.6
- obj.element-name: heading
- obj.language: en
- obj.specobject-type: heading
- ChapterName: 8.4.6 Specification relation groups (SpecRelationGroups)

##### tr--6d400e6f-d82a-44a1-8922-1185ec080fbf--8vama9O2LhMm: Specification relation groups (SpecRelationGroups) (provision)
The SpecRelationGroups of the type “relation-group-standard” contains:
- a)
a) “relation-group-internal”, where all internal relations of the document can be collected;
- b)
b) “relation-group-external”, where all relations to other documents can be collected (all other standards are also represented by SpecObjects of the type “document”).
- bib.al.original-language: en
- bib.dp.publication-date: 2025-03-01
- ids.document: 99200
- ids.element: o1749224057296-sub-8.4.6
- ids.language-synoptic: o1749224057296-sub-8.4.6
- ids.tracing: hash-3e952530ed07c132cf3838cdd753ecdcd40f18903618004ca82d0a878a50edc9
- obj.clause-number: 8.4.6
- obj.element-name: paragraph
- obj.language: en
- obj.modality: permission
- obj.normativity: normative
- obj.specobject-type: provision
- obj.transformation-issues: Possibly wrong modal verb
- use.business-process: undefined
- use.business-sector: undefined
- use.interaction: undefined
- use.location: undefined
- use.product-category: undefined
- use.product-life-cycle: undefined
- use.project-phase: undefined
- use.purpose: undefined

### prov-100000012-5397288d2c3b4f7: Class name abbreviations (in long names and identifiers) (heading)
- bib.al.original-language: en
- bib.dp.publication-date: 2025-03-01
- ids.document: 99200
- ids.element: o1749224057298-sub-8.5
- ids.language-synoptic: o1749224057298-sub-8.5
- ids.tracing: hash-372516f5224469b33f373056f56327e15d38fbf168e8c9410a9b567ca4fecff6
- obj.clause-number: 8.5
- obj.element-name: heading
- obj.language: en
- obj.specobject-type: heading
- ChapterName: 8.5 Class name abbreviations (in long names and identifiers)

#### tr--6d400e6f-d82a-44a1-8922-1185ec080fbf--uGsGjOJinUTk: Class name abbreviations (in long names and identifiers) (provision)
Class name abbreviations see Table 24.
- bib.al.original-language: en
- bib.dp.publication-date: 2025-03-01
- ids.document: 99200
- ids.element: o1749224057298-sub-8.5
- ids.language-synoptic: o1749224057298-sub-8.5
- ids.tracing: hash-7285ff935eb427e58c0fd96a8236a6888582bbeac8fdbe9e50b3521d5bec87d2
- obj.clause-number: 8.5
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-f028a325c22b450

#### prov-100000012-f028a325c22b450: Class name abbreviations (provision)
Table 24 — Class name abbreviations
| abbreviation | class name |
| --- | --- |
| ade | AttributeDefinitionEnumeration |
| ads | AttributeDefinitionString |
| adx | AttributeDefinitionXHTML |
| ddd | DatatypeDefinitionDate |
| dde | DatatypeDefinitionEnumeration |
| ddi | DatatypeDefinitionInteger |
| dd | DatatypeDefinitions |
| dds | DatatypeDefinitionString |
| ddx | DatatypeDefinitionXHTML |
| ev | EnumValue |
| rgt | RelationGroupTypes |
| st | SpecificationTypes |
| sot | SpecObjectTypes |
| srt | SpecRelationTypes |
| tr | harmonized prefix “tr” for “technical rule” |
- bib.al.original-language: en
- bib.dp.publication-date: 2025-03-01
- ids.document: 99200
- ids.element: o1749224057298-tab-24
- ids.language-synoptic: o1749224057298-tab-24
- ids.tracing: hash-5658ec8d2db9294bb6b2f4f7811c835d419b79142cab7ba09cf0b7c39519774d
- obj.clause-number: Table 24
- obj.element-name: table
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

## prov-100000012-a745655795d147d: Semantic interoperability (heading)
- bib.al.original-language: en
- bib.dp.publication-date: 2025-03-01
- ids.document: 99200
- ids.element: o1749224057301-sub-9
- ids.language-synoptic: o1749224057301-sub-9
- ids.tracing: hash-96efffa71a3cf0985fc99b0e105b0f6675740b34a0377c0ba0793a67a43849f1
- obj.clause-number: 9
- obj.element-name: heading
- obj.language: en
- obj.specobject-type: heading
- ChapterName: 9 Semantic interoperability

### prov-100000012-285e0301396b48d: Attribute conventions (heading)
- bib.al.original-language: en
- bib.dp.publication-date: 2025-03-01
- ids.document: 99200
- ids.element: o1749224057304-sub-9.1
- ids.language-synoptic: o1749224057304-sub-9.1
- ids.tracing: hash-54e073317634e68c6a4e14f7304ddb0e5e1b450e14230f1d918609820feecf3b
- obj.clause-number: 9.1
- obj.element-name: heading
- obj.language: en
- obj.specobject-type: heading
- ChapterName: 9.1 Attribute conventions

#### prov-100000012-1de5e80c85d94f3: Data field term; data field designation (heading)
- bib.al.original-language: en
- bib.dp.publication-date: 2025-03-01
- ids.document: 99200
- ids.element: o1749224057306-sub-9.1.1
- ids.language-synoptic: o1749224057306-sub-9.1.1
- ids.tracing: hash-8b0ad333a056814761254bb85b1ac5cf28673a0ae23428226eceeb794c55e5d9
- obj.clause-number: 9.1.1
- obj.element-name: heading
- obj.language: en
- obj.specobject-type: heading
- ChapterName: 9.1.1 Data field term; data field designation

##### tr--6d400e6f-d82a-44a1-8922-1185ec080fbf--nxQhg5wPIKb7: Data field term; data field designation (provision)
Data field terms (see 8.2) shall represent the standardized data field designations in the user’s natural language.
- bib.al.original-language: en
- bib.dp.publication-date: 2025-03-01
- ids.document: 99200
- ids.element: o1749224057306-sub-9.1.1
- ids.language-synoptic: o1749224057306-sub-9.1.1
- ids.tracing: hash-a00d46113cd677c14e4462b86918b9c4cb36ecc5b97f2a334b5a28c8e2e84332
- obj.clause-number: 9.1.1
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-252f89746a5e4d1

##### tr--6d400e6f-d82a-44a1-8922-1185ec080fbf--SWH7VdwCxUue: Data field term; data field designation (provision)
Data field terms (see 8.2) shall be specified in English language to improve international operability.
- bib.al.original-language: en
- bib.dp.publication-date: 2025-03-01
- ids.document: 99200
- ids.element: o1749224057306-sub-9.1.1
- ids.language-synoptic: o1749224057306-sub-9.1.1
- ids.tracing: hash-46759d1c90c3bde392b22ae74cf81704215e7d11bafe7c2ac6946dff08109d2c
- obj.clause-number: 9.1.1
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-252f89746a5e4d1

##### tr--6d400e6f-d82a-44a1-8922-1185ec080fbf--lGE6Yn7WZXEs: Data field term; data field designation (provision)
For the documentation, the data field terms (see 8.2):
- shall be specified in English, French and German to support at least the languages most commonly used for public standards;
- should be documented in other languages as appropriate for the relevant stakeholders.
- bib.al.original-language: en
- bib.dp.publication-date: 2025-03-01
- ids.document: 99200
- ids.element: o1749224057306-sub-9.1.1
- ids.language-synoptic: o1749224057306-sub-9.1.1
- ids.tracing: hash-4f648060b8a6fbe9ed2ec5fac0f057992f53e7fea08a263beb0c2e0ea4925352
- obj.clause-number: 9.1.1
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-252f89746a5e4d1

#### prov-100000012-10671b6f5e4849d: ReqIF™ attribute name (heading)
- bib.al.original-language: en
- bib.dp.publication-date: 2025-03-01
- ids.document: 99200
- ids.element: o1749224057308-sub-9.1.2
- ids.language-synoptic: o1749224057308-sub-9.1.2
- ids.tracing: hash-d5ce9554402d3cbf51dbdf58a452e0e534a7dec6d41e07a98be223977241e29f
- obj.clause-number: 9.1.2
- obj.element-name: heading
- obj.language: en
- obj.specobject-type: heading
- ChapterName: 9.1.2 ReqIF™ attribute name

##### tr--6d400e6f-d82a-44a1-8922-1185ec080fbf--BByqgnzViVQz: ReqIF™ attribute name (provision)
Attribute names (see 8.2) shall be specified in English language to improve international operability.
- bib.al.original-language: en
- bib.dp.publication-date: 2025-03-01
- ids.document: 99200
- ids.element: o1749224057308-sub-9.1.2
- ids.language-synoptic: o1749224057308-sub-9.1.2
- ids.tracing: hash-77c8c4bb767383e9b00e1ed3d2fb43f39ffd529688c08fe9e6cd5451bc922bd0
- obj.clause-number: 9.1.2
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-252f89746a5e4d1

##### tr--6d400e6f-d82a-44a1-8922-1185ec080fbf--4qRttEDOcRsy: ReqIF™ attribute name (provision)
Attribute names (see 8.2) shall only contain the characters dash, the digits 0 to 9 and the lower-case letters a to z [.\-0123456789a-z], except the adopted attributes ReqIF.ChapterName (9.6.1) and ReqIF.Text (9.6.2).
- bib.al.original-language: en
- bib.dp.publication-date: 2025-03-01
- ids.document: 99200
- ids.element: o1749224057308-sub-9.1.2
- ids.language-synoptic: o1749224057308-sub-9.1.2
- ids.tracing: hash-45fdbe66e8ec89df6aeb33364205097348ed86c0e0e326a084c28033f1e1024b
- obj.clause-number: 9.1.2
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-252f89746a5e4d1
- cross-reference -> prov-100000012-18bc1f195ab945a
- cross-reference -> prov-100000012-ed8a82f3f64d4bb

##### tr--6d400e6f-d82a-44a1-8922-1185ec080fbf--JlrpM3yX6f0b: ReqIF™ attribute name (provision)
The attribute names ReqIF.ChapterName (9.6.1) and ReqIF.Text (9.6.2) shall accord with the prostep ReqIF™ 1.2 guideline to ensure compatibility with as many target software as possible.
- bib.al.original-language: en
- bib.dp.publication-date: 2025-03-01
- ids.document: 99200
- ids.element: o1749224057308-sub-9.1.2
- ids.language-synoptic: o1749224057308-sub-9.1.2
- ids.tracing: hash-321fb4220c483c8fe13a6b223a70552bd6f71ec7f8479cbde1150ae9e01cfb8f
- obj.clause-number: 9.1.2
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-18bc1f195ab945a
- cross-reference -> prov-100000012-ed8a82f3f64d4bb

#### prov-100000012-7155fe8c97d5481: ReqIF™ data type (heading)
- bib.al.original-language: en
- bib.dp.publication-date: 2025-03-01
- ids.document: 99200
- ids.element: o1749224057310-sub-9.1.3
- ids.language-synoptic: o1749224057310-sub-9.1.3
- ids.tracing: hash-5633dc51191cffb20dfb3894ad9657f046465e2b47161bad060ecae32d7f282b
- obj.clause-number: 9.1.3
- obj.element-name: heading
- obj.language: en
- obj.specobject-type: heading
- ChapterName: 9.1.3 ReqIF™ data type

##### tr--6d400e6f-d82a-44a1-8922-1185ec080fbf--ROFV16LJkRPr: ReqIF™ data type (provision)
The ReqIF™ data type (see 8.2) shall be defined as:
- integer: if whole numbers may be applied only;
- value list (EnumValue): if users may select from fixed values only, so that the users can align values in the target systems easily;
- string: if users are allowed to change the values or values are not fixed;
- XHTML: if presentational markup according to XHTML™ 1.0 is required for an unambiguous interpretation of the value content.
- bib.al.original-language: en
- bib.dp.publication-date: 2025-03-01
- ids.document: 99200
- ids.element: o1749224057310-sub-9.1.3
- ids.language-synoptic: o1749224057310-sub-9.1.3
- ids.tracing: hash-41fed8fda5106e3a7a7e7594295db64dd1eeca49035f8a313c2ce1d1b980ae4d
- obj.clause-number: 9.1.3
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-252f89746a5e4d1

##### tr--6d400e6f-d82a-44a1-8922-1185ec080fbf--K0Fta9n7lDky: ReqIF™ data type (provision)
To maintain strings interoperable:
- attribute list values should only contain the characters space, period, dash, the digits 0 to 9 and the lower-case letters a to z [ .\-0123456789a-z].
- attribute string values or XHTML™ 1.0 content shall only contain UTF-8 characters required for the text in the respective language.
- bib.al.original-language: en
- bib.dp.publication-date: 2025-03-01
- ids.document: 99200
- ids.element: o1749224057310-sub-9.1.3
- ids.language-synoptic: o1749224057310-sub-9.1.3
- ids.tracing: hash-68c329fe2de2d166a2821e0c97ebad9e2ff791b4d21ba76e7642fa5587d29c0a
- obj.clause-number: 9.1.3
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### tr--6d400e6f-d82a-44a1-8922-1185ec080fbf--IntmwedWa6SK: ReqIF™ data type (provision)
The attribute values ReqIF.ChapterName (9.6.1) and ReqIF.Text (9.6.2) shall accord with the prostep ReqIF™ 1.2 guideline to ensure compatibility with as many target software as possible.
- bib.al.original-language: en
- bib.dp.publication-date: 2025-03-01
- ids.document: 99200
- ids.element: o1749224057310-sub-9.1.3
- ids.language-synoptic: o1749224057310-sub-9.1.3
- ids.tracing: hash-0b13f3d0901818d662bcf68e3be401e00b3b474cf439d2950be15807a6721d41
- obj.clause-number: 9.1.3
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-18bc1f195ab945a
- cross-reference -> prov-100000012-ed8a82f3f64d4bb

##### tr--6d400e6f-d82a-44a1-8922-1185ec080fbf--ZdSabOBJExBc: ReqIF™ data type (provision)
For value lists such the regions (see 8.3), the suppliers may update values to the state of the art if all stakeholders relevant for the interoperability context agree on the update.
- bib.al.original-language: en
- bib.dp.publication-date: 2025-03-01
- ids.document: 99200
- ids.element: o1749224057310-sub-9.1.3
- ids.language-synoptic: o1749224057310-sub-9.1.3
- ids.tracing: hash-49b71d2e0aaa93e8dfcec387f02991d615c1f6b46146d2d4534cd3ced7dc2423
- obj.clause-number: 9.1.3
- obj.element-name: paragraph
- obj.language: en
- obj.modality: permission
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-62b877911c1c4ff

#### prov-100000012-f048c54fb2ea4bc: ReqIF™ attribute value (heading)
- bib.al.original-language: en
- bib.dp.publication-date: 2025-03-01
- ids.document: 99200
- ids.element: o1749224057312-sub-9.1.4
- ids.language-synoptic: o1749224057312-sub-9.1.4
- ids.tracing: hash-c65e49265ebda5c798393759a1a1f877a59f6a1605f4e8b676910c69c754a481
- obj.clause-number: 9.1.4
- obj.element-name: heading
- obj.language: en
- obj.specobject-type: heading
- ChapterName: 9.1.4 ReqIF™ attribute value

##### tr--6d400e6f-d82a-44a1-8922-1185ec080fbf--liHisjFaT0JZ: ReqIF™ attribute value (provision)
If language-dependent information is concerned, all ReqIF™ attribute values (see 8.2 and 8.3) shall be specified in English language to improve international operability.
- bib.al.original-language: en
- bib.dp.publication-date: 2025-03-01
- ids.document: 99200
- ids.element: o1749224057312-sub-9.1.4
- ids.language-synoptic: o1749224057312-sub-9.1.4
- ids.tracing: hash-28346347cb5bedd618387b2ea62e358350a08500d97e90c8a4207ca7925b3060
- obj.clause-number: 9.1.4
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-252f89746a5e4d1
- cross-reference -> prov-100000012-62b877911c1c4ff

#### prov-100000012-f56b81d8c01f426: Default value for attributes (heading)
- bib.al.original-language: en
- bib.dp.publication-date: 2025-03-01
- ids.document: 99200
- ids.element: o1749224057314-sub-9.1.5
- ids.language-synoptic: o1749224057314-sub-9.1.5
- ids.tracing: hash-2c383b8926b686148cf9a62104ce0efd8d61f009729cbafa40ef9034f75f9945
- obj.clause-number: 9.1.5
- obj.element-name: heading
- obj.language: en
- obj.specobject-type: heading
- ChapterName: 9.1.5 Default value for attributes

##### tr--6d400e6f-d82a-44a1-8922-1185ec080fbf--6p7tNnsoLHCR: Default value for attributes (provision)
For all attributes that are required due to the schema or semantical specification, the attribute values (see 8.2) shall be set if no unambiguous default interpretation can be implied by the target software.
- bib.al.original-language: en
- bib.dp.publication-date: 2025-03-01
- ids.document: 99200
- ids.element: o1749224057314-sub-9.1.5
- ids.language-synoptic: o1749224057314-sub-9.1.5
- ids.tracing: hash-c23126167250cf9b4cfcc7c26673a76e5d2e4ad0f2d66f4f466ea3be8cc3ac51
- obj.clause-number: 9.1.5
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-252f89746a5e4d1

##### tr--6d400e6f-d82a-44a1-8922-1185ec080fbf--xAIf69KlxvbK: Default value for attributes (provision)
All attribute value lists (see 8.3) shall contain “undefined” as value, so that this value can be set if a value is required but no other semantical default value can be applied.
- bib.al.original-language: en
- bib.dp.publication-date: 2025-03-01
- ids.document: 99200
- ids.element: o1749224057314-sub-9.1.5
- ids.language-synoptic: o1749224057314-sub-9.1.5
- ids.tracing: hash-2b655391d692f1f0c9d9c25cce11cffc8095b8a995c6b963cea83605c7af69a5
- obj.clause-number: 9.1.5
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-62b877911c1c4ff

#### prov-100000012-7c302ac092bd465: Definition for attribute names and attribute values (heading)
- bib.al.original-language: en
- bib.dp.publication-date: 2025-03-01
- ids.document: 99200
- ids.element: o1749224057316-sub-9.1.6
- ids.language-synoptic: o1749224057316-sub-9.1.6
- ids.tracing: hash-86f7b828b111fca1d903eecbe7bb1424ef3677867a2e5fa582506362c02ae8a4
- obj.clause-number: 9.1.6
- obj.element-name: heading
- obj.language: en
- obj.specobject-type: heading
- ChapterName: 9.1.6 Definition for attribute names and attribute values

##### tr--6d400e6f-d82a-44a1-8922-1185ec080fbf--fCKGvyPVmObU: Definition for attribute names and attribute values (provision)
Definitions for attribute names (see 8.2) and for attribute values (see 8.3) shall be specified in English language to improve international operability.
- bib.al.original-language: en
- bib.dp.publication-date: 2025-03-01
- ids.document: 99200
- ids.element: o1749224057316-sub-9.1.6
- ids.language-synoptic: o1749224057316-sub-9.1.6
- ids.tracing: hash-2bffaef8426067131dba95ee53916fc3b1ffc845fa6096e398690f219d0b492c
- obj.clause-number: 9.1.6
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-252f89746a5e4d1
- cross-reference -> prov-100000012-62b877911c1c4ff

##### tr--6d400e6f-d82a-44a1-8922-1185ec080fbf--T14vzTt1Ybhv: Definition for attribute names and attribute values (provision)
All definitions shall be so unambiguous that different users can achieve the same interpretation to ensure the best possible interoperability between different stakeholders.
- bib.al.original-language: en
- bib.dp.publication-date: 2025-03-01
- ids.document: 99200
- ids.element: o1749224057316-sub-9.1.6
- ids.language-synoptic: o1749224057316-sub-9.1.6
- ids.tracing: hash-ad6719a37e85f050a0cb379062edf46d28379ff5a1c6a402278a92410f58bf57
- obj.clause-number: 9.1.6
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

#### prov-100000012-bcbed7eb58a44f4: Overflow of attribute values (heading)
- bib.al.original-language: en
- bib.dp.publication-date: 2025-03-01
- ids.document: 99200
- ids.element: o1749224057318-sub-9.1.7
- ids.language-synoptic: o1749224057318-sub-9.1.7
- ids.tracing: hash-fccdb9881169e7271ac1325efd46ed83b42b8aac5597ff2e363a3648c7d69c89
- obj.clause-number: 9.1.7
- obj.element-name: heading
- obj.language: en
- obj.specobject-type: heading
- ChapterName: 9.1.7 Overflow of attribute values

##### tr--6d400e6f-d82a-44a1-8922-1185ec080fbf--OL0VIz769WIg: Overflow of attribute values (provision)
If the original content in the public standard exceeds a defined string length, the text of the content shall be truncated and finished with three periods for the ellipsis (“…”) to fit into the available string length.
- bib.al.original-language: en
- bib.dp.publication-date: 2025-03-01
- ids.document: 99200
- ids.element: o1749224057318-sub-9.1.7
- ids.language-synoptic: o1749224057318-sub-9.1.7
- ids.tracing: hash-be52a3b585b4a24875fed55034242d3fd7b8d9b7bc64e57d9ea81af41701e2d7
- obj.clause-number: 9.1.7
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-a85caeb2a07d496: Overflow of attribute values (provision)
EXAMPLE:
Heading as UTF-8 string limited to a value below the 1024 bytes specified for headings:
“Xxx Xxxxx xxxxx Xxxxxxx xxx Xxxxx xxxxx Xxxxxxx xxx Xxxxx xxxxx Xxxxxxx xxx Xxxxx xxxxx Xxxxxxx xxx Xxxxx xxxxx Xxxxxxx xxx Xxxxx xxxxx Xxxxxxx xxx Xxxxx xxxxx Xxxxxxx xxx Xxxxx xxxxx Xxxxxxx xxx Xxxxx xxxxx Xxxxxxx xxx Xxxxx xxxxx Xxxxxxx xxx Xxxxx xxxxx Xxxxxxx xxx Xxxxx xxxxx Xxxxxxx xxx Xxxxx xxxxx Xxxxxxx xxx Xxxxx xxxxx Xxxxxxx xxx Xxxxx xxxxx Xxxxxxx xxx Xxxxx xxxxx Xxxxxxx xxx Xxxxx xxxxx Xxxxxxx xxx Xxxxx xxxxx Xxxxxxx xxx Xxxxx xxxxx Xxxxxxx xxx Xxxxx xxxxx Xxxxxxx xxx Xxxxx xxxxx Xxxxxxx xxx …”
- bib.al.original-language: en
- bib.dp.publication-date: 2025-03-01
- ids.document: 99200
- ids.element: o1749224057318-sub-9.1.7
- ids.language-synoptic: o1749224057318-sub-9.1.7
- ids.tracing: hash-f1308fbe4748fec98df3fc99ce0ce3d0037274a0adbd175d68046e6f70f634f8
- obj.clause-number: 9.1.7
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

##### tr--6d400e6f-d82a-44a1-8922-1185ec080fbf--XsMnEfG5m1PW: Overflow of attribute values (provision)
If an attribute value is reduced to fit into the specified value limits, the supplier should provide an error report so that the users can validate the impact of the limitation.
- bib.al.original-language: en
- bib.dp.publication-date: 2025-03-01
- ids.document: 99200
- ids.element: o1749224057318-sub-9.1.7
- ids.language-synoptic: o1749224057318-sub-9.1.7
- ids.tracing: hash-da7da96ddc4842598c71fef694e39dc3cd7035e89628f74cf6254306c693482b
- obj.clause-number: 9.1.7
- obj.element-name: paragraph
- obj.language: en
- obj.modality: recommendation
- obj.normativity: normative
- obj.specobject-type: provision
- use.business-process: undefined
- use.business-sector: undefined
- use.interaction: undefined
- use.location: undefined
- use.product-category: undefined
- use.product-life-cycle: undefined
- use.project-phase: undefined
- use.purpose: undefined

#### prov-100000012-369460760ffd4a2: Localization of attributes (heading)
- bib.al.original-language: en
- bib.dp.publication-date: 2025-03-01
- ids.document: 99200
- ids.element: o1749224057320-sub-9.1.8
- ids.language-synoptic: o1749224057320-sub-9.1.8
- ids.tracing: hash-2a647e8b98a576cd6e70dde9df4fc2c4eb1488f6c51afb805c90f19f5013f506
- obj.clause-number: 9.1.8
- obj.element-name: heading
- obj.language: en
- obj.specobject-type: heading
- ChapterName: 9.1.8 Localization of attributes

##### tr--6d400e6f-d82a-44a1-8922-1185ec080fbf--p2NLlJzL6HAE: Localization of attributes (provision)
The supplier shall locate the attributes according to 8.2.
- bib.al.original-language: en
- bib.dp.publication-date: 2025-03-01
- ids.document: 99200
- ids.element: o1749224057320-sub-9.1.8
- ids.language-synoptic: o1749224057320-sub-9.1.8
- ids.tracing: hash-c0ccdc2a930128abfa413cc7ad24ba59cf8c050d31c3bbf0d03141f9b2bcfb86
- obj.clause-number: 9.1.8
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-252f89746a5e4d1

##### tr--6d400e6f-d82a-44a1-8922-1185ec080fbf--XN9GIZykV5Nc: Localization of attributes (provision)
The supplier shall locate the bibliographic document metadata (see 8.2.1.4) for each SpecObject in the ReqIF™ file depending on the type of the SpecObject (see 8.2.1.2).
- bib.al.original-language: en
- bib.dp.publication-date: 2025-03-01
- ids.document: 99200
- ids.element: o1749224057320-sub-9.1.8
- ids.language-synoptic: o1749224057320-sub-9.1.8
- ids.tracing: hash-ead9e0d259f2a406c2be6b890773798098a0dc2f66eaa5b6a6bd35159e840b8c
- obj.clause-number: 9.1.8
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-ac76d054ec4c4b2
- cross-reference -> prov-100000012-2f90c5903f8d49c

##### tr--6d400e6f-d82a-44a1-8922-1185ec080fbf--fvP8TdxXlu6A: Localization of attributes (provision)
If the attribute obj.specobject-type (8.2.1.2) has the value (see 9.7.8):
- “document”, the supplier shall set the bibliographic document metadata according to 8.2.1.4 at the SpecObject with the title page metadata and at the specification of the ReqIF™ file.
- “heading”, the supplier shall set only the attributes bib.di.document-identifier (8.2.1.4) and bib.dp.publication-date (8.2.1.4) at the SpecObject with the heading of a provision.
- “provision”, the supplier shall set the bibliographic document metadata according to 8.2.1.4 at the SpecObject with the content of a provision itself.
- bib.al.original-language: en
- bib.dp.publication-date: 2025-03-01
- ids.document: 99200
- ids.element: o1749224057320-sub-9.1.8
- ids.language-synoptic: o1749224057320-sub-9.1.8
- ids.tracing: hash-041338b873906826bf4daa7f80fe1a3794438551d169161c6b5614150d80e5ac
- obj.clause-number: 9.1.8
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-2f90c5903f8d49c
- cross-reference -> prov-100000012-b62f8267193c47d
- cross-reference -> prov-100000012-ac76d054ec4c4b2

### prov-100000012-2cb50e2fc93b465: Attribute or content outputs (heading)
- bib.al.original-language: en
- bib.dp.publication-date: 2025-03-01
- ids.document: 99200
- ids.element: o1749224057323-sub-9.2
- ids.language-synoptic: o1749224057323-sub-9.2
- ids.tracing: hash-501694e22019c23095855e6e24f128cbcb32efba81b47eabf16529fc1f1b3c79
- obj.clause-number: 9.2
- obj.element-name: heading
- obj.language: en
- obj.specobject-type: heading
- ChapterName: 9.2 Attribute or content outputs

#### prov-100000012-379fbd391ce7432: Data field term or definition (ReqIF:DESC) (heading)
- bib.al.original-language: en
- bib.dp.publication-date: 2025-03-01
- ids.document: 99200
- ids.element: o1749224057325-sub-9.2.1
- ids.language-synoptic: o1749224057325-sub-9.2.1
- ids.tracing: hash-4dc57c334ebb336277f31100657d48090196424cf93036af17d702d6a75f04fc
- obj.clause-number: 9.2.1
- obj.element-name: heading
- obj.language: en
- obj.specobject-type: heading
- ChapterName: 9.2.1 Data field term or definition (ReqIF:DESC)

##### tr--6d400e6f-d82a-44a1-8922-1185ec080fbf--sFTWOjzffwMG: Data field term or definition (ReqIF:DESC) (provision)
Either the data field term (see 8.2), the definition (see 8.2) or both information concatenated shall be output to the ReqIF™ file as value of the attribute DESC at the elements according to 11.3.
- bib.al.original-language: en
- bib.dp.publication-date: 2025-03-01
- ids.document: 99200
- ids.element: o1749224057325-sub-9.2.1
- ids.language-synoptic: o1749224057325-sub-9.2.1
- ids.tracing: hash-a392310f1f33679ac287dbb54601cb5ddde1d4e8f2b1121eec90aac0622e9663
- obj.clause-number: 9.2.1
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-252f89746a5e4d1
- cross-reference -> prov-100000012-da658d9b664941f

##### prov-100000012-4232b30c618c42d: Data field term or definition (ReqIF:DESC) (provision)
EXAMPLE 1:
The data field term (see 8.2) term is the value of the attribute DESC:
<ATTRIBUTE-DEFINITION-ENUMERATION DESC="Modality; bindingness" ...>
- bib.al.original-language: en
- bib.dp.publication-date: 2025-03-01
- ids.document: 99200
- ids.element: o1749224057325-sub-9.2.1
- ids.language-synoptic: o1749224057325-sub-9.2.1
- ids.tracing: hash-c97d82c8e992b55b230672419f0663dd23b324aa986cbb361eda5ff6709eaefa
- obj.clause-number: 9.2.1
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
- cross-reference -> prov-100000012-252f89746a5e4d1

##### prov-100000012-babf30a12b1341e: Data field term or definition (ReqIF:DESC) (provision)
EXAMPLE 2:
The definition (see 8.2) is the value of the attribute DESC:
<ATTRIBUTE-DEFINITION-ENUMERATION DESC="level of obligation for a governing provision in the standard model " IDENTIFIER="tr--ade--provision--obj.modality" ...>
- bib.al.original-language: en
- bib.dp.publication-date: 2025-03-01
- ids.document: 99200
- ids.element: o1749224057325-sub-9.2.1
- ids.language-synoptic: o1749224057325-sub-9.2.1
- ids.tracing: hash-432f0531ddb76e61723889c6f9451b2e6e8805973b097e70d0695aea28420573
- obj.clause-number: 9.2.1
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
- cross-reference -> prov-100000012-252f89746a5e4d1

##### prov-100000012-b2e5eaf97856494: Data field term or definition (ReqIF:DESC) (provision)
EXAMPLE 3:
The data field term (see 8.2) and the definition (see 8.2) concatenated are the value of the attribute DESC:
<ATTRIBUTE-DEFINITION-ENUMERATION DESC="Modality; bindingness: level of obligation for a governing provision in the standard model " ...>
- bib.al.original-language: en
- bib.dp.publication-date: 2025-03-01
- ids.document: 99200
- ids.element: o1749224057325-sub-9.2.1
- ids.language-synoptic: o1749224057325-sub-9.2.1
- ids.tracing: hash-d440fa6d6516d3f390dce9f6a66b5c67ea06e956147e584930a4c5901c4f6c69
- obj.clause-number: 9.2.1
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
- cross-reference -> prov-100000012-252f89746a5e4d1

#### prov-100000012-0bedb46361434ab: Identifier (ReqIF:IDENTIFIER) (heading)
- bib.al.original-language: en
- bib.dp.publication-date: 2025-03-01
- ids.document: 99200
- ids.element: o1749224057327-sub-9.2.2
- ids.language-synoptic: o1749224057327-sub-9.2.2
- ids.tracing: hash-857f7e323a7bc74e751b55836e573b9e93d3f68b1cbfe5ec7ce31d285ec7af8d
- obj.clause-number: 9.2.2
- obj.element-name: heading
- obj.language: en
- obj.specobject-type: heading
- ChapterName: 9.2.2 Identifier (ReqIF:IDENTIFIER)

##### tr--6d400e6f-d82a-44a1-8922-1185ec080fbf--M0c2Rr4yzmzo: Identifier (ReqIF:IDENTIFIER) (provision)
The identifier (see 8.2) shall be output to the ReqIF™ file as value of the attribute IDENTIFIER at the elements according to 11.3.
- bib.al.original-language: en
- bib.dp.publication-date: 2025-03-01
- ids.document: 99200
- ids.element: o1749224057327-sub-9.2.2
- ids.language-synoptic: o1749224057327-sub-9.2.2
- ids.tracing: hash-b37e3bbd5c6dd2b0860ce173525d962866a6a8f5e08a6f10b4c5dc95e4114fd7
- obj.clause-number: 9.2.2
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-252f89746a5e4d1
- cross-reference -> prov-100000012-da658d9b664941f

##### prov-100000012-0f4a12c4f8a84dc: Identifier (ReqIF:IDENTIFIER) (provision)
EXAMPLE 1:
The identifier (see 8.3) term is the value of the attribute DESC:
<DATATYPE-DEFINITION-ENUMERATION IDENTIFIER="tr--dde--modality" LAST-CHANGE="..." LONG-NAME="modality"> <SPECIFIED-VALUES> ... <ENUM-VALUE IDENTIFIER="tr--ev--modality--requirement" LAST-CHANGE="..." LONG-NAME="requirement"> <PROPERTIES> <EMBEDDED-VALUE KEY="7" OTHER-CONTENT="requirement"/> </PROPERTIES> </ENUM-VALUE> ... </SPECIFIED-VALUES> </ DATATYPE-DEFINITION-ENUMERATION>
- bib.al.original-language: en
- bib.dp.publication-date: 2025-03-01
- ids.document: 99200
- ids.element: o1749224057327-sub-9.2.2
- ids.language-synoptic: o1749224057327-sub-9.2.2
- ids.tracing: hash-8b85eb03c693244f3994b81240e7222ae0ff5200fd08482fa9ccdbed82a7b93a
- obj.clause-number: 9.2.2
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
- cross-reference -> prov-100000012-62b877911c1c4ff

##### tr--6d400e6f-d82a-44a1-8922-1185ec080fbf--I7G5QGiF3i2X: Identifier (ReqIF:IDENTIFIER) (provision)
The identifier (see 8.3) shall be output to the ReqIF™ file as content of the elements according to 11.3.
- bib.al.original-language: en
- bib.dp.publication-date: 2025-03-01
- ids.document: 99200
- ids.element: o1749224057327-sub-9.2.2
- ids.language-synoptic: o1749224057327-sub-9.2.2
- ids.tracing: hash-9f41f8746cedac060b9368989a5a96dae769b06e38483a3c1829f66f46c5effa
- obj.clause-number: 9.2.2
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-62b877911c1c4ff
- cross-reference -> prov-100000012-da658d9b664941f

##### prov-100000012-f1da4fd6e7ed47e: Identifier (ReqIF:IDENTIFIER) (provision)
EXAMPLE 2:
The identifier (see 8.3) is the content of exemplary elements:
<ATTRIBUTE-VALUE-ENUMERATION> <VALUES> <ENUM-VALUE-REF>tr--ev--modality--requirement</ENUM-VALUE-REF> </VALUES> <DEFINITION> <ATTRIBUTE-DEFINITION-ENUMERATION-REF>tr--ade--provision--obj.modality </ATTRIBUTE-DEFINITION-ENUMERATION-REF> </DEFINITION> </ATTRIBUTE-VALUE-ENUMERATION>
- bib.al.original-language: en
- bib.dp.publication-date: 2025-03-01
- ids.document: 99200
- ids.element: o1749224057327-sub-9.2.2
- ids.language-synoptic: o1749224057327-sub-9.2.2
- ids.tracing: hash-728cc080a78de84720f4daaf4aa9b5874f6923b16ec12efa597d6fed74b4287c
- obj.clause-number: 9.2.2
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
- cross-reference -> prov-100000012-62b877911c1c4ff

##### tr--6d400e6f-d82a-44a1-8922-1185ec080fbf--luYej8kgV6qC: Identifier (ReqIF:IDENTIFIER) (provision)
The attribute identifiers shall be implemented according to 8.4, using the harmonized class name abbreviations for this application (see 8.5).
- bib.al.original-language: en
- bib.dp.publication-date: 2025-03-01
- ids.document: 99200
- ids.element: o1749224057327-sub-9.2.2
- ids.language-synoptic: o1749224057327-sub-9.2.2
- ids.tracing: hash-944f934c6a3ecf2b028f37149b97b18796300b8f6fb5b847a6f25b9a28bf9c99
- obj.clause-number: 9.2.2
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-e0c5df8513054b8
- cross-reference -> prov-100000012-5397288d2c3b4f7

#### prov-100000012-c25b6db61e074df: ReqIF™ attribute name (ReqIF:LONG-NAME) (heading)
- bib.al.original-language: en
- bib.dp.publication-date: 2025-03-01
- ids.document: 99200
- ids.element: o1749224057329-sub-9.2.3
- ids.language-synoptic: o1749224057329-sub-9.2.3
- ids.tracing: hash-50e4415dc4d3052d90f23783f64a384a7552370bdea87f52af6d3b49f6c6914c
- obj.clause-number: 9.2.3
- obj.element-name: heading
- obj.language: en
- obj.specobject-type: heading
- ChapterName: 9.2.3 ReqIF™ attribute name (ReqIF:LONG-NAME)

##### tr--6d400e6f-d82a-44a1-8922-1185ec080fbf--kE7XmehfUD8n: ReqIF™ attribute name (ReqIF:LONG-NAME) (provision)
The attribute name (see 8.2) shall be output to the ReqIF™ file as value of the attribute LONG-NAME at the elements according to 11.3.
- bib.al.original-language: en
- bib.dp.publication-date: 2025-03-01
- ids.document: 99200
- ids.element: o1749224057329-sub-9.2.3
- ids.language-synoptic: o1749224057329-sub-9.2.3
- ids.tracing: hash-56f7a2389016c66081b6ca28cea1e6a5efbafba766e952e3db65ef89ec1321e6
- obj.clause-number: 9.2.3
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-252f89746a5e4d1
- cross-reference -> prov-100000012-da658d9b664941f

##### prov-100000012-8d0f6cabba91424: ReqIF™ attribute name (ReqIF:LONG-NAME) (provision)
EXAMPLE: <DATATYPE-DEFINITION-ENUMERATION IDENTIFIER="tr--dde--modality" LAST-CHANGE="..." LONG-NAME="modality">
- bib.al.original-language: en
- bib.dp.publication-date: 2025-03-01
- ids.document: 99200
- ids.element: o1749224057329-sub-9.2.3
- ids.language-synoptic: o1749224057329-sub-9.2.3
- ids.tracing: hash-594f4cb31966b6d923ea5aecdd90f5435c85c80dc02a520a84ba04b4e8951ff1
- obj.clause-number: 9.2.3
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

#### prov-100000012-ebd39dce6f2041a: ReqIF™ attribute value (ReqIF:LONG-NAME) (heading)
- bib.al.original-language: en
- bib.dp.publication-date: 2025-03-01
- ids.document: 99200
- ids.element: o1749224057331-sub-9.2.4
- ids.language-synoptic: o1749224057331-sub-9.2.4
- ids.tracing: hash-658abc60d9f19624e6109f487769abc1bdd4c00d24367db7762865d42902b932
- obj.clause-number: 9.2.4
- obj.element-name: heading
- obj.language: en
- obj.specobject-type: heading
- ChapterName: 9.2.4 ReqIF™ attribute value (ReqIF:LONG-NAME)

##### tr--6d400e6f-d82a-44a1-8922-1185ec080fbf--DT4WUhnj2egP: ReqIF™ attribute value (ReqIF:LONG-NAME) (provision)
The attribute value (see 8.2) shall be output to the ReqIF™ file as value of the attribute LONG-NAME at the elements according to 11.3.
- bib.al.original-language: en
- bib.dp.publication-date: 2025-03-01
- ids.document: 99200
- ids.element: o1749224057331-sub-9.2.4
- ids.language-synoptic: o1749224057331-sub-9.2.4
- ids.tracing: hash-7e65aa20c76bd9bab2417f0078279e6434396459d832a4fed6fb1b4afecd5a0b
- obj.clause-number: 9.2.4
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-252f89746a5e4d1
- cross-reference -> prov-100000012-da658d9b664941f

##### prov-100000012-13f135c7cd134d3: ReqIF™ attribute value (ReqIF:LONG-NAME) (provision)
EXAMPLE: <ENUM-VALUE IDENTIFIER="tr--ev--modality--requirement" LAST-CHANGE="..." LONG-NAME="requirement">
- bib.al.original-language: en
- bib.dp.publication-date: 2025-03-01
- ids.document: 99200
- ids.element: o1749224057331-sub-9.2.4
- ids.language-synoptic: o1749224057331-sub-9.2.4
- ids.tracing: hash-623136c92d513cf4762c46d2297d6984b3fd1cb92118154f132863e0147c8187
- obj.clause-number: 9.2.4
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

#### prov-100000012-b2b38a33f23d48b: Definition (ReqIF:DESC) (heading)
- bib.al.original-language: en
- bib.dp.publication-date: 2025-03-01
- ids.document: 99200
- ids.element: o1749224057333-sub-9.2.5
- ids.language-synoptic: o1749224057333-sub-9.2.5
- ids.tracing: hash-559511ae1ab10f3ca150c4fea399c0d326184fc5a993904ce0c9f8ca976fb1d0
- obj.clause-number: 9.2.5
- obj.element-name: heading
- obj.language: en
- obj.specobject-type: heading
- ChapterName: 9.2.5 Definition (ReqIF:DESC)

##### tr--6d400e6f-d82a-44a1-8922-1185ec080fbf--26fFe5on4VEg: Definition (ReqIF:DESC) (provision)
For attribute values, the definition (see 8.3) shall be output to the ReqIF™ file as value of the attribute DESC at the elements according to 11.3.
- bib.al.original-language: en
- bib.dp.publication-date: 2025-03-01
- ids.document: 99200
- ids.element: o1749224057333-sub-9.2.5
- ids.language-synoptic: o1749224057333-sub-9.2.5
- ids.tracing: hash-eecfd7f880c225c1b5a9c574e375033ae4f4ddc538d734268dba4e0c3651bdfd
- obj.clause-number: 9.2.5
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-62b877911c1c4ff
- cross-reference -> prov-100000012-da658d9b664941f

##### prov-100000012-c29f90e5c353409: Definition (ReqIF:DESC) (provision)
EXAMPLE:
For DESC see 9.2.1 Example 2 or Example 3.
- bib.al.original-language: en
- bib.dp.publication-date: 2025-03-01
- ids.document: 99200
- ids.element: o1749224057333-sub-9.2.5
- ids.language-synoptic: o1749224057333-sub-9.2.5
- ids.tracing: hash-6705202eeaede858485b57f4da054e59d1fe98157478617e2abd5b9d7a4ee724
- obj.clause-number: 9.2.5
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
- cross-reference -> prov-100000012-babf30a12b1341e
- cross-reference -> prov-100000012-b2e5eaf97856494

#### prov-100000012-0ca04e8ca7bc4ee: Is-editable (ReqIF:IS-EDITABLE) (heading)
- bib.al.original-language: en
- bib.dp.publication-date: 2025-03-01
- ids.document: 99200
- ids.element: o1749224057335-sub-9.2.6
- ids.language-synoptic: o1749224057335-sub-9.2.6
- ids.tracing: hash-b7813250ce54c93f2d4b31b00d3dcc24d4169fbccb8630cdf348c7fbd3adf647
- obj.clause-number: 9.2.6
- obj.element-name: heading
- obj.language: en
- obj.specobject-type: heading
- ChapterName: 9.2.6 Is-editable (ReqIF:IS-EDITABLE)

##### tr--6d400e6f-d82a-44a1-8922-1185ec080fbf--oJGpVv2EvVU4: Is-editable (ReqIF:IS-EDITABLE) (provision)
The attribute permissions (see 8.2) shall be output to the ReqIF™ file as value of the attribute IS-EDITABLE at the elements according to 11.3.
- bib.al.original-language: en
- bib.dp.publication-date: 2025-03-01
- ids.document: 99200
- ids.element: o1749224057335-sub-9.2.6
- ids.language-synoptic: o1749224057335-sub-9.2.6
- ids.tracing: hash-91ef71569e140b88a0009b489104546836995d79c78d0e74f1ec2a1e07c4f599
- obj.clause-number: 9.2.6
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-252f89746a5e4d1
- cross-reference -> prov-100000012-da658d9b664941f

##### tr--6d400e6f-d82a-44a1-8922-1185ec080fbf--C2xMQ5OKisoN: Is-editable (ReqIF:IS-EDITABLE) (provision)
Conflicting values for the attribute IS-EDITABLE should be resolved according to the prostep ReqIF™ 1.2 guideline.
- bib.al.original-language: en
- bib.dp.publication-date: 2025-03-01
- ids.document: 99200
- ids.element: o1749224057335-sub-9.2.6
- ids.language-synoptic: o1749224057335-sub-9.2.6
- ids.tracing: hash-578b9e8d19ff3ea4ea9680a12f7cf4e2f322976be1835180b8f23b4ce1b27945
- obj.clause-number: 9.2.6
- obj.element-name: paragraph
- obj.language: en
- obj.modality: recommendation
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-245b3742e1004c5: Is-editable (ReqIF:IS-EDITABLE) (provision)
EXAMPLE: <ATTRIBUTE-DEFINITION-ENUMERATION DESC="Modality; bindingness" IDENTIFIER="tr--ade--provision--obj.modality" IS-EDITABLE="true" LAST-CHANGE="..." LONG-NAME="obj.modality" MULTI-VALUED="false">
- bib.al.original-language: en
- bib.dp.publication-date: 2025-03-01
- ids.document: 99200
- ids.element: o1749224057335-sub-9.2.6
- ids.language-synoptic: o1749224057335-sub-9.2.6
- ids.tracing: hash-0ad06c08eef72c04b195a40418bbf90930aed9f42dceaabc95858481092767e4
- obj.clause-number: 9.2.6
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

#### prov-100000012-1798ec4811c54e3: Last change (ReqIF:LAST-CHANGE) (heading)
- bib.al.original-language: en
- bib.dp.publication-date: 2025-03-01
- ids.document: 99200
- ids.element: o1749224057337-sub-9.2.7
- ids.language-synoptic: o1749224057337-sub-9.2.7
- ids.tracing: hash-1571fa044f3e84b632b41dba1d6b447d790ea8d110af5cd6f98c8c776e1b9435
- obj.clause-number: 9.2.7
- obj.element-name: heading
- obj.language: en
- obj.specobject-type: heading
- ChapterName: 9.2.7 Last change (ReqIF:LAST-CHANGE)

##### tr--6d400e6f-d82a-44a1-8922-1185ec080fbf--l6BMfAnX4wak: Last change (ReqIF:LAST-CHANGE) (provision)
According to the OMG ReqIF™ 1.2 specification, the attribute change information shall be output to the ReqIF™ file as value of the attribute LAST-CHANGE at the elements according to 11.3.
- bib.al.original-language: en
- bib.dp.publication-date: 2025-03-01
- ids.document: 99200
- ids.element: o1749224057337-sub-9.2.7
- ids.language-synoptic: o1749224057337-sub-9.2.7
- ids.tracing: hash-187d4ae11807a31d9356406c9dbeb6e1382d8381fe3bb791656fecb14a03e7b7
- obj.clause-number: 9.2.7
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-da658d9b664941f

##### tr--6d400e6f-d82a-44a1-8922-1185ec080fbf--BrSaQnXZXVpK: Last change (ReqIF:LAST-CHANGE) (provision)
Since the change information equals either the creation or the change of the element, it may only be used for managing changes for the same version of a document but not across different versions of the same document.
- bib.al.original-language: en
- bib.dp.publication-date: 2025-03-01
- ids.document: 99200
- ids.element: o1749224057337-sub-9.2.7
- ids.language-synoptic: o1749224057337-sub-9.2.7
- ids.tracing: hash-101cbe33a3a7dcb19fe2f8391e702c15a73b66cccbc7dd3215f08b139fe03ef3
- obj.clause-number: 9.2.7
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### tr--6d400e6f-d82a-44a1-8922-1185ec080fbf--ugKUFniesDVG: Last change (ReqIF:LAST-CHANGE) (provision)
To manage SpecObjects of the same fragment across all versions of the same document, the tracing ID (see 9.10.5) can be used if tracing IDs are provided by the supplier.
- bib.al.original-language: en
- bib.dp.publication-date: 2025-03-01
- ids.document: 99200
- ids.element: o1749224057337-sub-9.2.7
- ids.language-synoptic: o1749224057337-sub-9.2.7
- ids.tracing: hash-4e4f7603cf40ded1a8728984be5e5d2c287ed3d89640d8db57ef53a418cf99d3
- obj.clause-number: 9.2.7
- obj.element-name: paragraph
- obj.language: en
- obj.modality: permission
- obj.normativity: normative
- obj.specobject-type: provision
- obj.transformation-issues: Possibly wrong modal verb
- use.business-process: undefined
- use.business-sector: undefined
- use.interaction: undefined
- use.location: undefined
- use.product-category: undefined
- use.product-life-cycle: undefined
- use.project-phase: undefined
- use.purpose: undefined
- cross-reference -> prov-100000012-754296aabcb5401

#### prov-100000012-6aa97194de8a440: Maximum length (ReqIF:MAX-LENGTH) (heading)
- bib.al.original-language: en
- bib.dp.publication-date: 2025-03-01
- ids.document: 99200
- ids.element: o1749224057339-sub-9.2.8
- ids.language-synoptic: o1749224057339-sub-9.2.8
- ids.tracing: hash-e3a628bfd6748679b06daea38d1453729755970333774f49bd852ff2ffc6479b
- obj.clause-number: 9.2.8
- obj.element-name: heading
- obj.language: en
- obj.specobject-type: heading
- ChapterName: 9.2.8 Maximum length (ReqIF:MAX-LENGTH)

##### tr--6d400e6f-d82a-44a1-8922-1185ec080fbf--jFhCKcPYVrlu: Maximum length (ReqIF:MAX-LENGTH) (provision)
For ReqIF™ data type string attributes, the maximum length (see 8.2) shall be output to the ReqIF™ file as value of the attribute MAX-LENGTH at the element <DATATYPE-DEFINITION-STRING>.
- bib.al.original-language: en
- bib.dp.publication-date: 2025-03-01
- ids.document: 99200
- ids.element: o1749224057339-sub-9.2.8
- ids.language-synoptic: o1749224057339-sub-9.2.8
- ids.tracing: hash-73a437775e1ec094b65d7e2b3ff53c78d143aefbd4606b5373c988e27cb27848
- obj.clause-number: 9.2.8
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-252f89746a5e4d1

#### prov-100000012-4afe24c64ba2488: Value list using multiple or single values (ReqIF:MULTI-VALUED) (heading)
- bib.al.original-language: en
- bib.dp.publication-date: 2025-03-01
- ids.document: 99200
- ids.element: o1749224057341-sub-9.2.9
- ids.language-synoptic: o1749224057341-sub-9.2.9
- ids.tracing: hash-28688bf7400a6bee86f60137ea289689c05601f45e2ddec7a75f2adde30a898c
- obj.clause-number: 9.2.9
- obj.element-name: heading
- obj.language: en
- obj.specobject-type: heading
- ChapterName: 9.2.9 Value list using multiple or single values (ReqIF:MULTI-VALUED)

##### prov-100000012-3b156bfb8aed4ed: Value list using multiple or single values (ReqIF:MULTI-VALUED) (provision)
- If the ReqIF™ data type (see 8.2) is specified as “enum-multi”, the attribute MULTI-VALUED at the element <ATTRIBUTE-DEFINITION-ENUMERATION> shall be set to the value “true”.
- If the ReqIF™ data type (see 8.2) is specified as “enum-single”, the attribute MULTI-VALUED at the element <ATTRIBUTE-DEFINITION-ENUMERATION> shall be set to the value “false”.
- bib.al.original-language: en
- bib.dp.publication-date: 2025-03-01
- ids.document: 99200
- ids.element: o1749224057341-sub-9.2.9
- ids.language-synoptic: o1749224057341-sub-9.2.9
- ids.tracing: hash-141e46211ac19af96401aebafe5ddc964084a34b2f3c3f6e448281ffc57434ca
- obj.clause-number: 9.2.9
- obj.element-name: unordered-list
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-252f89746a5e4d1

#### prov-100000012-60c7e7fa36114b4: Other content (ReqIF:OTHER-CONTENT) (heading)
- bib.al.original-language: en
- bib.dp.publication-date: 2025-03-01
- ids.document: 99200
- ids.element: o1749224057343-sub-9.2.10
- ids.language-synoptic: o1749224057343-sub-9.2.10
- ids.tracing: hash-704a30ddf31baadca6a3566c5e02c8358899d76663d7cb99817612c16729cd78
- obj.clause-number: 9.2.10
- obj.element-name: heading
- obj.language: en
- obj.specobject-type: heading
- ChapterName: 9.2.10 Other content (ReqIF:OTHER-CONTENT)

##### tr--6d400e6f-d82a-44a1-8922-1185ec080fbf--pbLPmvNsVCoX: Other content (ReqIF:OTHER-CONTENT) (provision)
According to the OMG ReqIF™ 1.2 specification,
- the attribute name (see 8.2) should be output to ReqIF™ as value of the attribute OTHER-CONTENT at the element <EMBEDDED-VALUE/> (see Example).
- the counter from 1 to n should be output to ReqIF™ as value of the attribute KEY at the element <EMBEDDED-VALUE/> (see Example).
- bib.al.original-language: en
- bib.dp.publication-date: 2025-03-01
- ids.document: 99200
- ids.element: o1749224057343-sub-9.2.10
- ids.language-synoptic: o1749224057343-sub-9.2.10
- ids.tracing: hash-665469b1f180967b3c31b884b2c4866d89a47c187bcf5264c5f24054930b4490
- obj.clause-number: 9.2.10
- obj.element-name: paragraph
- obj.language: en
- obj.modality: recommendation
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-252f89746a5e4d1

##### prov-100000012-2a27ceb059a64f8: Other content (ReqIF:OTHER-CONTENT) (provision)
EXAMPLE:
The value of the attribute LONG-NAME represented as value of the attributes KEY and OTHER-CONTENT at the element <EMBEDDED-VALUE>:
<DATATYPE-DEFINITION-ENUMERATION IDENTIFIER="tr--dde--modality" LAST-CHANGE="..." LONG-NAME="modality"> <SPECIFIED-VALUES> ... <ENUM-VALUE IDENTIFIER="tr--ev--modality--requirement" LAST-CHANGE="..." LONG-NAME="requirement"> <PROPERTIES> <EMBEDDED-VALUE KEY="7" OTHER-CONTENT="requirement"/> </PROPERTIES> </ENUM-VALUE> ... </SPECIFIED-VALUES> </DATATYPE-DEFINITION-ENUMERATION>
- bib.al.original-language: en
- bib.dp.publication-date: 2025-03-01
- ids.document: 99200
- ids.element: o1749224057343-sub-9.2.10
- ids.language-synoptic: o1749224057343-sub-9.2.10
- ids.tracing: hash-2606a08fdd25040ee0fb829a00cadb8f316e1420bb22ef3cc4f2094e8a92b122
- obj.clause-number: 9.2.10
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### prov-100000012-a1413c74654c453: File format (heading)
- bib.al.original-language: en
- bib.dp.publication-date: 2025-03-01
- ids.document: 99200
- ids.element: o1749224057346-sub-9.3
- ids.language-synoptic: o1749224057346-sub-9.3
- ids.tracing: hash-6da496b39d3a9510c23165c589291c0064b57a1727593abaa8a4a482b42c2005
- obj.clause-number: 9.3
- obj.element-name: heading
- obj.language: en
- obj.specobject-type: heading
- ChapterName: 9.3 File format

#### prov-100000012-5c416b52b4d542c: Form of the ReqIF™ file (heading)
- bib.al.original-language: en
- bib.dp.publication-date: 2025-03-01
- ids.document: 99200
- ids.element: o1749224057348-sub-9.3.1
- ids.language-synoptic: o1749224057348-sub-9.3.1
- ids.tracing: hash-34cbda77fda5d90fb90117ec450b3b89d78345eefbdfbd411c9b0d765c305f11
- obj.clause-number: 9.3.1
- obj.element-name: heading
- obj.language: en
- obj.specobject-type: heading
- ChapterName: 9.3.1 Form of the ReqIF™ file

##### tr--6d400e6f-d82a-44a1-8922-1185ec080fbf--qggxoaPilE2n: Form of the ReqIF™ file (provision)
The ReqIF™ for a public standard shall be provided as zipped archive file.
- bib.al.original-language: en
- bib.dp.publication-date: 2025-03-01
- ids.document: 99200
- ids.element: o1749224057348-sub-9.3.1
- ids.language-synoptic: o1749224057348-sub-9.3.1
- ids.tracing: hash-a440eef7bcab86987a6995e88a7599afd6d18928950a39a00ed383d204ac303c
- obj.clause-number: 9.3.1
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### tr--6d400e6f-d82a-44a1-8922-1185ec080fbf--sKHX3fhzkk16: Form of the ReqIF™ file (provision)
The zipped archive file for a public standard shall use the usual file suffix “.reqifz”.
- bib.al.original-language: en
- bib.dp.publication-date: 2025-03-01
- ids.document: 99200
- ids.element: o1749224057348-sub-9.3.1
- ids.language-synoptic: o1749224057348-sub-9.3.1
- ids.tracing: hash-3f26662319a5f4185bb1fe0da5519f782f8337a63ce20a523897dcce962b4889
- obj.clause-number: 9.3.1
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### tr--6d400e6f-d82a-44a1-8922-1185ec080fbf--oMWO7IE6rUCS: Form of the ReqIF™ file (provision)
The zipped archive file for a public standard shall contain:
- the ReqIF™ file for one language variant of the public standard;
- all directories and files which are referenced as external entities from the ReqIF™ file.
- bib.al.original-language: en
- bib.dp.publication-date: 2025-03-01
- ids.document: 99200
- ids.element: o1749224057348-sub-9.3.1
- ids.language-synoptic: o1749224057348-sub-9.3.1
- ids.tracing: hash-fdf14c0232ee984dae521dcd86a56dea3841ef520a854afc56260bf8ba792f18
- obj.clause-number: 9.3.1
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### tr--6d400e6f-d82a-44a1-8922-1185ec080fbf--72OyQNKaslcY: Form of the ReqIF™ file (provision)
The ReqIF™ file shall use the usual file suffix “.reqif”.
- bib.al.original-language: en
- bib.dp.publication-date: 2025-03-01
- ids.document: 99200
- ids.element: o1749224057348-sub-9.3.1
- ids.language-synoptic: o1749224057348-sub-9.3.1
- ids.tracing: hash-a66c9120fbfe1890ba17c126ccecaa06de4287e6ddc9ef7095075a78f2c8b868
- obj.clause-number: 9.3.1
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### tr--6d400e6f-d82a-44a1-8922-1185ec080fbf--xqI3aDTgAhYG: Form of the ReqIF™ file (provision)
To ensure interoperability, the ReqIF™ file shall contain only relative paths to the required external entities.
- bib.al.original-language: en
- bib.dp.publication-date: 2025-03-01
- ids.document: 99200
- ids.element: o1749224057348-sub-9.3.1
- ids.language-synoptic: o1749224057348-sub-9.3.1
- ids.tracing: hash-5bfc1bc62d17a7e629d1259fe89d772c2268c4a3ee0416ae431f3935d8f40ae8
- obj.clause-number: 9.3.1
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### tr--6d400e6f-d82a-44a1-8922-1185ec080fbf--kVoSeqtGxgja: Form of the ReqIF™ file (provision)
To provide multiple language variants for a public standard, the supplier shall supply a separate zipped archive file for each language variant with one ReqIF™ file and the referenced external entities.
- bib.al.original-language: en
- bib.dp.publication-date: 2025-03-01
- ids.document: 99200
- ids.element: o1749224057348-sub-9.3.1
- ids.language-synoptic: o1749224057348-sub-9.3.1
- ids.tracing: hash-7cce60a47581bca1ee1987b9a9a81842fcf087e82e7f620fc58b496248eb9084
- obj.clause-number: 9.3.1
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

#### prov-100000012-de26c648df4e43e: Header of the ReqIF™ file (heading)
- bib.al.original-language: en
- bib.dp.publication-date: 2025-03-01
- ids.document: 99200
- ids.element: o1749224057350-sub-9.3.2
- ids.language-synoptic: o1749224057350-sub-9.3.2
- ids.tracing: hash-f3947e0b61cf4c472ffc7f47b47116b0a2868d97586f590656d91712e2fe387b
- obj.clause-number: 9.3.2
- obj.element-name: heading
- obj.language: en
- obj.specobject-type: heading
- ChapterName: 9.3.2 Header of the ReqIF™ file

##### tr--6d400e6f-d82a-44a1-8922-1185ec080fbf--0gvnarkNfACK: Header of the ReqIF™ file (provision)
For the ReqIF™ header, the document identifier (see 9.10.1) shall be output to the ReqIF™ file as value of the attribute IDENTIFIER at the element <REQ-IF-HEADER>.
- bib.al.original-language: en
- bib.dp.publication-date: 2025-03-01
- ids.document: 99200
- ids.element: o1749224057350-sub-9.3.2
- ids.language-synoptic: o1749224057350-sub-9.3.2
- ids.tracing: hash-bcfa2c27364bcd69ae3b1926765019fe9ae4f2a5d4c68a1d87d96d4b58e72bf8
- obj.clause-number: 9.3.2
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-81f28831f2ef4b3

##### tr--6d400e6f-d82a-44a1-8922-1185ec080fbf--g9ZPdUmv7l19: Header of the ReqIF™ file (provision)
For the ReqIF™ header, a date and time stamp for the creation shall be output to the ReqIF™ file as content at the element <CREATION-TIME>.
- bib.al.original-language: en
- bib.dp.publication-date: 2025-03-01
- ids.document: 99200
- ids.element: o1749224057350-sub-9.3.2
- ids.language-synoptic: o1749224057350-sub-9.3.2
- ids.tracing: hash-2b72d367225e2453b26541babd7abeb3b1d895e4c287810ed12ded60998ef6c4
- obj.clause-number: 9.3.2
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### tr--6d400e6f-d82a-44a1-8922-1185ec080fbf--gGgOVV48AleK: Header of the ReqIF™ file (provision)
For the ReqIF™ header, the software (see 9.11.3) shall be output to the ReqIF™ file as content of the element:
- <COMMENT>;
- <REQ-IF-TOOL-ID>;
- <SOURCE-TOOL-ID>.
- bib.al.original-language: en
- bib.dp.publication-date: 2025-03-01
- ids.document: 99200
- ids.element: o1749224057350-sub-9.3.2
- ids.language-synoptic: o1749224057350-sub-9.3.2
- ids.tracing: hash-aac8689237f39a36fb75b73bfb72a8e95dac3b60f6b656671aff80a7c496077a
- obj.clause-number: 9.3.2
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-b101fc3b61ca445

##### tr--6d400e6f-d82a-44a1-8922-1185ec080fbf--0J3OVW2blFoy: Header of the ReqIF™ file (provision)
For the ReqIF™ header, ReqIF™ version shall be output to the ReqIF™ file as content of the element <REQ-IF-VERSION> (see Example).
- bib.al.original-language: en
- bib.dp.publication-date: 2025-03-01
- ids.document: 99200
- ids.element: o1749224057350-sub-9.3.2
- ids.language-synoptic: o1749224057350-sub-9.3.2
- ids.tracing: hash-795e1b38421debb4e93a93cb7112511b1b79639f80a7ac708ac23263f14ba5c8
- obj.clause-number: 9.3.2
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### tr--6d400e6f-d82a-44a1-8922-1185ec080fbf--Od43NQQyR4br: Header of the ReqIF™ file (provision)
For the ReqIF™ header, key information for a quick identification of the document (see 8.2.1.4) shall be output to the ReqIF™ file as content of the element <TITLE>.
- bib.al.original-language: en
- bib.dp.publication-date: 2025-03-01
- ids.document: 99200
- ids.element: o1749224057350-sub-9.3.2
- ids.language-synoptic: o1749224057350-sub-9.3.2
- ids.tracing: hash-558deb4a0afdb3be53f0ec933f942341dcaba6ac32b86c2dd67ce4c58a78d09b
- obj.clause-number: 9.3.2
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-ac76d054ec4c4b2

##### prov-100000012-cbecd528e7c3408: Header of the ReqIF™ file (provision)
EXAMPLE: <?xml version="1.0" encoding="UTF-8"?> <REQ-IF xmlns="http://www.omg.org/spec/ReqIF/20110401/reqif.xsd" xmlns:mml="http://www.w3.org/1998/Math/MathML" xmlns:xhtml="http://www.w3.org/1999/xhtml"> <THE-HEADER> <REQ-IF-HEADER IDENTIFIER="tr--e11d82e5--h"> <COMMENT>created by sts2reqif</COMMENT> <CREATION-TIME>2024-11-20T16:27:13.227+01:00</CREATION-TIME> <REQ-IF-TOOL-ID>sts2reqif 3.0.0</REQ-IF-TOOL-ID> <REQ-IF-VERSION>1.0</REQ-IF-VERSION> <SOURCE-TOOL-ID>sts2reqif</SOURCE-TOOL-ID> <TITLE>ISO 1463:1995-01, Metallic and oxide coatings – Measurement of ...</TITLE> </REQ-IF-HEADER> </THE-HEADER> ... </REQ-IF>
- bib.al.original-language: en
- bib.dp.publication-date: 2025-03-01
- ids.document: 99200
- ids.element: o1749224057350-sub-9.3.2
- ids.language-synoptic: o1749224057350-sub-9.3.2
- ids.tracing: hash-5164bc646bc1247d13996e45896210127c5c8a5ff48c139b5e4d3fe2de70ec27
- obj.clause-number: 9.3.2
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

#### prov-100000012-6a37406f1fb5451: Tool extensions (heading)
- bib.al.original-language: en
- bib.dp.publication-date: 2025-03-01
- ids.document: 99200
- ids.element: o1749224057352-sub-9.3.3
- ids.language-synoptic: o1749224057352-sub-9.3.3
- ids.tracing: hash-f46fc8b7b651be239208b0d36d5d22e390896c468d5afa9d0bb62b6e2109190b
- obj.clause-number: 9.3.3
- obj.element-name: heading
- obj.language: en
- obj.specobject-type: heading
- ChapterName: 9.3.3 Tool extensions

##### tr--6d400e6f-d82a-44a1-8922-1185ec080fbf--hScdF2KQVQUo: Tool extensions (provision)
The element <REQ-IF-TOOL-EXTENSION> is not used by this specification.
- bib.al.original-language: en
- bib.dp.publication-date: 2025-03-01
- ids.document: 99200
- ids.element: o1749224057352-sub-9.3.3
- ids.language-synoptic: o1749224057352-sub-9.3.3
- ids.tracing: hash-5d72c63b29a9d70ae0a3e8da45ff13703249a08a80e724b3ed6667a334df2164
- obj.clause-number: 9.3.3
- obj.element-name: paragraph
- obj.language: en
- obj.modality: permission
- obj.normativity: normative
- obj.specobject-type: provision
- use.business-process: undefined
- use.business-sector: undefined
- use.interaction: undefined
- use.location: undefined
- use.product-category: undefined
- use.product-life-cycle: undefined
- use.project-phase: undefined
- use.purpose: undefined

##### tr--6d400e6f-d82a-44a1-8922-1185ec080fbf--VukTibImo8wZ: Tool extensions (provision)
The element <REQ-IF-TOOL-EXTENSION> may be used according to the prostep ReqIF™ 1.2 guideline if the interoperability between the relevant stakeholders is not jeopardized.
- bib.al.original-language: en
- bib.dp.publication-date: 2025-03-01
- ids.document: 99200
- ids.element: o1749224057352-sub-9.3.3
- ids.language-synoptic: o1749224057352-sub-9.3.3
- ids.tracing: hash-469aee8b71744c5c84af24995402bf2de7947d5062b56817922f61df7b9c5035
- obj.clause-number: 9.3.3
- obj.element-name: paragraph
- obj.language: en
- obj.modality: permission
- obj.normativity: normative
- obj.specobject-type: provision
- use.business-process: undefined
- use.business-sector: undefined
- use.interaction: undefined
- use.location: undefined
- use.product-category: undefined
- use.product-life-cycle: undefined
- use.project-phase: undefined
- use.purpose: undefined

### prov-100000012-4bf1554dc23443f: Fragmentation of documents into provisions (SpecObjects) (heading)
- bib.al.original-language: en
- bib.dp.publication-date: 2025-03-01
- ids.document: 99200
- ids.element: o1749224057355-sub-9.4
- ids.language-synoptic: o1749224057355-sub-9.4
- ids.tracing: hash-4bde85a5e4fd63cf269cffeb495feeaa1cdcef4b8e6001c0c52526fb1af66e03
- obj.clause-number: 9.4
- obj.element-name: heading
- obj.language: en
- obj.specobject-type: heading
- ChapterName: 9.4 Fragmentation of documents into provisions (SpecObjects)

#### prov-100000012-8766b23bf88e40a: Fragmentation options (heading)
- bib.al.original-language: en
- bib.dp.publication-date: 2025-03-01
- ids.document: 99200
- ids.element: o1749224057358-sub-9.4.1
- ids.language-synoptic: o1749224057358-sub-9.4.1
- ids.tracing: hash-f2b1619f405bdf9e14c2d750645b46e4b054180991006468f629625adaa49c26
- obj.clause-number: 9.4.1
- obj.element-name: heading
- obj.language: en
- obj.specobject-type: heading
- ChapterName: 9.4.1 Fragmentation options

##### prov-100000012-f6c75a9523fc4a5: Division-wise fragmentation (unused) (heading)
- bib.al.original-language: en
- bib.dp.publication-date: 2025-03-01
- ids.document: 99200
- ids.element: o1749224057360-sub-9.4.1.1
- ids.language-synoptic: o1749224057360-sub-9.4.1.1
- ids.tracing: hash-fc502c482edac3e102060731122fd5f71d65657f13247fa37dd28810a51cb939
- obj.clause-number: 9.4.1.1
- obj.element-name: heading
- obj.language: en
- obj.specobject-type: heading
- ChapterName: 9.4.1.1 Division-wise fragmentation (unused)

###### tr--6d400e6f-d82a-44a1-8922-1185ec080fbf--fu5Luy5vdcJf: Division-wise fragmentation (unused) (provision)
Each division such as a clause, subclause or annex is output as a SpecObject.
- bib.al.original-language: en
- bib.dp.publication-date: 2025-03-01
- ids.document: 99200
- ids.element: o1749224057360-sub-9.4.1.1
- ids.language-synoptic: o1749224057360-sub-9.4.1.1
- ids.tracing: hash-52f29781aa642df51b0a8ea69470346cd65fb6dbb99feb638351feb09bb415bc
- obj.clause-number: 9.4.1.1
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-5e01855e805a424: Paragraph-wise fragmentation (unused) (heading)
- bib.al.original-language: en
- bib.dp.publication-date: 2025-03-01
- ids.document: 99200
- ids.element: o1749224057362-sub-9.4.1.2
- ids.language-synoptic: o1749224057362-sub-9.4.1.2
- ids.tracing: hash-53da6e8ba4726936f7b35a63b52e25eff94434ee24f22ebd0e1348719e226596
- obj.clause-number: 9.4.1.2
- obj.element-name: heading
- obj.language: en
- obj.specobject-type: heading
- ChapterName: 9.4.1.2 Paragraph-wise fragmentation (unused)

###### tr--6d400e6f-d82a-44a1-8922-1185ec080fbf--rjba2H09PAiZ: Paragraph-wise fragmentation (unused) (provision)
Each paragraph and each paragraph-like block or display element such as enumeration items, notes, examples, ordering details, standard designations, warnings etc. is output as a SpecObject.
- bib.al.original-language: en
- bib.dp.publication-date: 2025-03-01
- ids.document: 99200
- ids.element: o1749224057362-sub-9.4.1.2
- ids.language-synoptic: o1749224057362-sub-9.4.1.2
- ids.tracing: hash-c13cf1f5e1de714a5496e340b1a3185c574715b911275e678080ebc0d25f5101
- obj.clause-number: 9.4.1.2
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-0a1f4dc8db3c4a2: Sentence-wise fragmentation (harmonized standard method) (heading)
- bib.al.original-language: en
- bib.dp.publication-date: 2025-03-01
- ids.document: 99200
- ids.element: o1749224057364-sub-9.4.1.3
- ids.language-synoptic: o1749224057364-sub-9.4.1.3
- ids.tracing: hash-d748ee4b7623bf5e38ecce8e2f39b9eab746976b57c5d04dc38f8929790691a5
- obj.clause-number: 9.4.1.3
- obj.element-name: heading
- obj.language: en
- obj.specobject-type: heading
- ChapterName: 9.4.1.3 Sentence-wise fragmentation (harmonized standard method)

###### tr--6d400e6f-d82a-44a1-8922-1185ec080fbf--K5oZcJtKhygl: Sentence-wise fragmentation (harmonized standard method) (provision)
The sentence-wise fragmentation shall be applied for public standards, except if all stakeholders relevant for the interoperability context agree on one of the alternative options (see 9.4.1.1 or 9.4.1.2).
- bib.al.original-language: en
- bib.dp.publication-date: 2025-03-01
- ids.document: 99200
- ids.element: o1749224057364-sub-9.4.1.3
- ids.language-synoptic: o1749224057364-sub-9.4.1.3
- ids.tracing: hash-99c1a9a0180a2eb57f952b8e3b1ec631f7b4397cc5947dd8ff23d7f6b6a88d84
- obj.clause-number: 9.4.1.3
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-f6c75a9523fc4a5
- cross-reference -> prov-100000012-5e01855e805a424

#### prov-100000012-2b2580247a7e403: Sentence determination (heading)
- bib.al.original-language: en
- bib.dp.publication-date: 2025-03-01
- ids.document: 99200
- ids.element: o1749224057366-sub-9.4.2
- ids.language-synoptic: o1749224057366-sub-9.4.2
- ids.tracing: hash-94f217351d9c14b89208be60c9e608a7872e3d58b4a760b61eafc634367493ca
- obj.clause-number: 9.4.2
- obj.element-name: heading
- obj.language: en
- obj.specobject-type: heading
- ChapterName: 9.4.2 Sentence determination

##### prov-100000012-3249dbd56e3147e: Sentence determination (provision)
- If the sentence is not the partial content of a so-called atomic element (see 9.4.3), each sentence shall be output as a SpecObject.
- If the sentence is the partial content of a so-called atomic element (see 9.4.3), the whole atomic element shall be output as one SpecObject.
- If the sentence would run out of a so-called terminating element (see 9.4.4), it shall be treated according to 9.4.4, since an expression may not run out of its logical context.
- bib.al.original-language: en
- bib.dp.publication-date: 2025-03-01
- ids.document: 99200
- ids.element: o1749224057366-sub-9.4.2
- ids.language-synoptic: o1749224057366-sub-9.4.2
- ids.tracing: hash-49fc4d9ff19e4396dc7c93c936f4af92d40b499a328863bd0b782a168eb15bc2
- obj.clause-number: 9.4.2
- obj.element-name: unordered-list
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-6c210d928624496
- cross-reference -> prov-100000012-2fc9d9a25cd1492

##### prov-100000012-abaa5059a5c246d: Sentence determination (provision)
EXAMPLE 1:
The Sentence begins in the paragraph and is ended in a list contained therein.
- bib.al.original-language: en
- bib.dp.publication-date: 2025-03-01
- ids.document: 99200
- ids.element: o1749224057366-sub-9.4.2
- ids.language-synoptic: o1749224057366-sub-9.4.2
- ids.tracing: hash-fbc096b3ed72eaff2cd3fed8f1e695378d4041fe99859c79000acc76879e5c06
- obj.clause-number: 9.4.2
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

##### prov-100000012-b5e271f4bdb347d: Sentence determination (provision)
EXAMPLE 2:
The Sentence begins in the paragraph and is only ended in a following paragraphs or display elements contained therein.
- bib.al.original-language: en
- bib.dp.publication-date: 2025-03-01
- ids.document: 99200
- ids.element: o1749224057366-sub-9.4.2
- ids.language-synoptic: o1749224057366-sub-9.4.2
- ids.tracing: hash-3ffe0035d8be8f04d46690eb73e62de09156560492afeaaee0ac0c6b12670392
- obj.clause-number: 9.4.2
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

##### prov-100000012-f2edc880da3f4c0: Sentence determination (provision)
EXAMPLE 3:
The Sentence begins in a table cell and is only ended in a succeeding table cell.
- bib.al.original-language: en
- bib.dp.publication-date: 2025-03-01
- ids.document: 99200
- ids.element: o1749224057366-sub-9.4.2
- ids.language-synoptic: o1749224057366-sub-9.4.2
- ids.tracing: hash-d7d16d9587c7fe4c8e9b264e7a87146e6c47b1a78d36f3ddc04f0a2eafc96537
- obj.clause-number: 9.4.2
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

##### tr--6d400e6f-d82a-44a1-8922-1185ec080fbf--5xnM05v5FLH7: Sentence determination (provision)
If the sentence has been determined using natural language processing, sentences should:
- contain at least three words;
- not be terminated by common abbreviations finished by a period;
- not be terminated by a period which represents a decimal separator sign;
- not be finished by sentence signs which are part of a specific technical notation;
- be terminated by true sentence signs, only.
- bib.al.original-language: en
- bib.dp.publication-date: 2025-03-01
- ids.document: 99200
- ids.element: o1749224057366-sub-9.4.2
- ids.language-synoptic: o1749224057366-sub-9.4.2
- ids.tracing: hash-90656a8374e54c0c0e1a03a8d51f072080d66a5b398e3f3d9b5f149b67968769
- obj.clause-number: 9.4.2
- obj.element-name: paragraph
- obj.language: en
- obj.modality: recommendation
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-c14709a81f254f7: Sentence determination (provision)
EXAMPLE 4:
Not terminating abbreviation within the sentence:
“Apples, pears, plums etc. are all fruits”.
- bib.al.original-language: en
- bib.dp.publication-date: 2025-03-01
- ids.document: 99200
- ids.element: o1749224057366-sub-9.4.2
- ids.language-synoptic: o1749224057366-sub-9.4.2
- ids.tracing: hash-d811ce3ee11d2b2b94d4c5cdc1be2163b6ba183b9f0c5e036634a159545178b0
- obj.clause-number: 9.4.2
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

##### prov-100000012-bbfd56a99a4e4b2: Sentence determination (provision)
EXAMPLE 5:
Terminating abbreviation at the end of the sentence.
“Fruits are apples, pears, plums, etc. Everything else are vegetables.”
- bib.al.original-language: en
- bib.dp.publication-date: 2025-03-01
- ids.document: 99200
- ids.element: o1749224057366-sub-9.4.2
- ids.language-synoptic: o1749224057366-sub-9.4.2
- ids.tracing: hash-00b23cbdc589d09b24034e9243d193a4555c3fdd0f5b659ae3c0449b785940fc
- obj.clause-number: 9.4.2
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

##### prov-100000012-75f8eb3f13294ce: Sentence determination (provision)
EXAMPLE 6:
Not terminating abbreviation within the sentence:
“The stakeholders are founding a Corp. and not an Inc.”
- bib.al.original-language: en
- bib.dp.publication-date: 2025-03-01
- ids.document: 99200
- ids.element: o1749224057366-sub-9.4.2
- ids.language-synoptic: o1749224057366-sub-9.4.2
- ids.tracing: hash-a195950087b2d8ff79df87e294ebb20b7f377e3d5088e0200f8a44d9b3e8733b
- obj.clause-number: 9.4.2
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

##### prov-100000012-2a538bd3dbd043d: Sentence determination (provision)
EXAMPLE 7:
Not terminating abbreviation within the sentence:
“The stakeholders are founding an Inc., but we need at least seven founding members.”
- bib.al.original-language: en
- bib.dp.publication-date: 2025-03-01
- ids.document: 99200
- ids.element: o1749224057366-sub-9.4.2
- ids.language-synoptic: o1749224057366-sub-9.4.2
- ids.tracing: hash-f3bd69e41929c09d034bbb07c2d65008a5cb9ab9b0158c93fcea21791674661e
- obj.clause-number: 9.4.2
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

##### prov-100000012-17414eecd862429: Sentence determination (provision)
EXAMPLE 8:
Terminating abbreviation at the end of the sentence:
“The stakeholders are founding an Inc. However, they need at least seven founding members.”
- bib.al.original-language: en
- bib.dp.publication-date: 2025-03-01
- ids.document: 99200
- ids.element: o1749224057366-sub-9.4.2
- ids.language-synoptic: o1749224057366-sub-9.4.2
- ids.tracing: hash-27a72349834280e5c0019b1178c456eed5ad922833c6553bcf5a691c448b2605
- obj.clause-number: 9.4.2
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

##### prov-100000012-3fe93f98ec7440c: Sentence determination (provision)
EXAMPLE 9:
Not terminating decimal separator within the sentence:
“The users should ignore values below 4.1 °C in the measurements.”
- bib.al.original-language: en
- bib.dp.publication-date: 2025-03-01
- ids.document: 99200
- ids.element: o1749224057366-sub-9.4.2
- ids.language-synoptic: o1749224057366-sub-9.4.2
- ids.tracing: hash-ae8016501b52f457b7adf0653135f23c0b1a46d1e2b4ed33b4ba97b87ae5979a
- obj.clause-number: 9.4.2
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

##### prov-100000012-b801712896b24aa: Sentence determination (provision)
EXAMPLE 10:
Not terminating specific technical notation within the sentence:
“If the router is set to the default gateway, the users can visit http://192.168.0.1 to access it.”
- bib.al.original-language: en
- bib.dp.publication-date: 2025-03-01
- ids.document: 99200
- ids.element: o1749224057366-sub-9.4.2
- ids.language-synoptic: o1749224057366-sub-9.4.2
- ids.tracing: hash-2ff07aa56b193eabd9326fc5ba046482b73be58ce46c955c0b67d0d0062ff8cf
- obj.clause-number: 9.4.2
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

#### prov-100000012-6c210d928624496: “Atomic element” (heading)
- bib.al.original-language: en
- bib.dp.publication-date: 2025-03-01
- ids.document: 99200
- ids.element: o1749224057368-sub-9.4.3
- ids.language-synoptic: o1749224057368-sub-9.4.3
- ids.tracing: hash-a6d2bf7eb067fcbcff25fd2ee4ae3f4c0f7ac87cfd0a3f8620bc032fd05a1d15
- obj.clause-number: 9.4.3
- obj.element-name: heading
- obj.language: en
- obj.specobject-type: heading
- ChapterName: 9.4.3 “Atomic element”

##### tr--6d400e6f-d82a-44a1-8922-1185ec080fbf--felpXOeDjpCA: “Atomic element” (provision)
The following elements shall not be split into sentences, so that no sentence is ripped-out of its logical context:
- elements of terminological entries up to any sub-entry, i. e. term, definition, and other information according to DIN ISO 10241-1;
- designation systems such as ordering details or standard designations (see Example);
- paired expressions and descriptions in descriptive enumerations;
- bibliographic entries in the list of documents;
- listings.
- bib.al.original-language: en
- bib.dp.publication-date: 2025-03-01
- ids.document: 99200
- ids.element: o1749224057368-sub-9.4.3
- ids.language-synoptic: o1749224057368-sub-9.4.3
- ids.tracing: hash-c93f46587272b902ad2ee9da21726dffeb44c63efdaf8ae30d748e5068ca6c5a
- obj.clause-number: 9.4.3
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-f8e21987be1245c: “Atomic element” (provision)
EXAMPLE:
“Screw ISO 1580-M5 × 20-4,8”
- bib.al.original-language: en
- bib.dp.publication-date: 2025-03-01
- ids.document: 99200
- ids.element: o1749224057368-sub-9.4.3
- ids.language-synoptic: o1749224057368-sub-9.4.3
- ids.tracing: hash-9793aa7b38e92269c55e976c638f9e620a8aa00a664b10317a9d6c166d7d1fea
- obj.clause-number: 9.4.3
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

#### prov-100000012-2fc9d9a25cd1492: “Terminating element” (heading)
- bib.al.original-language: en
- bib.dp.publication-date: 2025-03-01
- ids.document: 99200
- ids.element: o1749224057370-sub-9.4.4
- ids.language-synoptic: o1749224057370-sub-9.4.4
- ids.tracing: hash-782f3ca921bf39574257314fa6fba80ddab31f75ac2f860b93f4cf7da8096450
- obj.clause-number: 9.4.4
- obj.element-name: heading
- obj.language: en
- obj.specobject-type: heading
- ChapterName: 9.4.4 “Terminating element”

##### tr--6d400e6f-d82a-44a1-8922-1185ec080fbf--pECJ2exaLHpP: “Terminating element” (provision)
Sentences shall be terminated by the following elements, so that no expression can run out of its logical context:
- “atomic element” (see 9.4.3);
- figure;
- example;
- note;
- division (all types of clauses, annexes, and terminological entries);
- table;
- warning.
- bib.al.original-language: en
- bib.dp.publication-date: 2025-03-01
- ids.document: 99200
- ids.element: o1749224057370-sub-9.4.4
- ids.language-synoptic: o1749224057370-sub-9.4.4
- ids.tracing: hash-72d08510121ce538428378bbda8164931cb13596c1c7bff6088fde00b5cfb1ac
- obj.clause-number: 9.4.4
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-6c210d928624496

#### prov-100000012-3d83b6e8af98445: Enumerations (lists) in the text (heading)
- bib.al.original-language: en
- bib.dp.publication-date: 2025-03-01
- ids.document: 99200
- ids.element: o1749224057373-sub-9.4.5
- ids.language-synoptic: o1749224057373-sub-9.4.5
- ids.tracing: hash-ec3e2ca98ca3c10df042544460649886f842776d6ce284b28539319dc195e16b
- obj.clause-number: 9.4.5
- obj.element-name: heading
- obj.language: en
- obj.specobject-type: heading
- ChapterName: 9.4.5 Enumerations (lists) in the text

##### prov-100000012-a2ed100a4155469: Enumeration as part of a provision (heading)
- bib.al.original-language: en
- bib.dp.publication-date: 2025-03-01
- ids.document: 99200
- ids.element: o1749224057375-sub-9.4.5.1
- ids.language-synoptic: o1749224057375-sub-9.4.5.1
- ids.tracing: hash-6df4048c003c6521d49d974c8908f73502ae5b95394cf030bb4e2c3c68858c82
- obj.clause-number: 9.4.5.1
- obj.element-name: heading
- obj.language: en
- obj.specobject-type: heading
- ChapterName: 9.4.5.1 Enumeration as part of a provision

###### tr--6d400e6f-d82a-44a1-8922-1185ec080fbf--K4jSptpsvwF9: Enumeration as part of a provision (provision)
If the sentence runs from an introductory paragraph text into the enumeration (see Example 1), either:
- the paragraph and whole enumeration shall be output with all items as one SpecObject; or
- the introductory paragraph may be moved at the beginning of each item (see Example 2) so that each item may be handled as separate provision (see 9.4.5.2) if the users prefer normalized provisions.
- bib.al.original-language: en
- bib.dp.publication-date: 2025-03-01
- ids.document: 99200
- ids.element: o1749224057375-sub-9.4.5.1
- ids.language-synoptic: o1749224057375-sub-9.4.5.1
- ids.tracing: hash-aba236af0f9e45a99fd8a0b81828cb4d6d02797428f4c08ab3d137236cfc9594
- obj.clause-number: 9.4.5.1
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-079e99e7c20b463
- cross-reference -> prov-100000012-64378e9d46eb4a0
- cross-reference -> prov-100000012-9508067fdbc3484

###### prov-100000012-079e99e7c20b463: Enumeration as part of a provision (provision)
EXAMPLE 1:
Enumeration is part of a provision:
“The test report shall include the following information:
- a)
a) the sample location on the sample piece from which the microsection was made;
- b)
b) the coating thickness measured at each location (7.3) in µm (in mm if greater than 1 mm) and the length of the section over which the measurement was made;
- c)
c) the local coating thickness, i. e. the arithmetic mean value of the measured coating thicknesses.”
- bib.al.original-language: en
- bib.dp.publication-date: 2025-03-01
- ids.document: 99200
- ids.element: o1749224057375-sub-9.4.5.1
- ids.language-synoptic: o1749224057375-sub-9.4.5.1
- ids.tracing: hash-1afe08043dd1a46114a0fb72076d7a95ea1fa59ecb80da4c36eade02c1670175
- obj.clause-number: 9.4.5.1
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
- cross-reference -> prov-100000012-5a64252d1a58418

###### prov-100000012-64378e9d46eb4a0: Enumeration as part of a provision (provision)
EXAMPLE 2:
Original non-singular provision and normalized singular provisions:
| original paragraph with a list in the source | normalized provisions in the target |
| --- | --- |
| “The organization shall retain documented information: - a a on the results of the review; - b b on any new requirements for the products and services.” | - a a “The organization shall retain documented information on the results of the review. - b b The organization shall retain documented information on any new requirements for the products and services.” |
- bib.al.original-language: en
- bib.dp.publication-date: 2025-03-01
- ids.document: 99200
- ids.element: o1749224057375-sub-9.4.5.1
- ids.language-synoptic: o1749224057375-sub-9.4.5.1
- ids.tracing: hash-a203e8d0900e7f4a365a79cebe375d79d33e3e0338097277f0b918b1f5086192
- obj.clause-number: 9.4.5.1
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

##### prov-100000012-9508067fdbc3484: Each item of an enumeration as a separate provision (heading)
- bib.al.original-language: en
- bib.dp.publication-date: 2025-03-01
- ids.document: 99200
- ids.element: o1749224057377-sub-9.4.5.2
- ids.language-synoptic: o1749224057377-sub-9.4.5.2
- ids.tracing: hash-9a3e37a075aff7008801814fac5134b984f4d8a2f76f193b00a1b35eb0de17cf
- obj.clause-number: 9.4.5.2
- obj.element-name: heading
- obj.language: en
- obj.specobject-type: heading
- ChapterName: 9.4.5.2 Each item of an enumeration as a separate provision

###### tr--6d400e6f-d82a-44a1-8922-1185ec080fbf--SO9fmfb0jlb0: Each item of an enumeration as a separate provision (provision)
If each item of an enumeration is recognized as a complete sentence (see Example), for the whole enumeration each item shall be output as a separate SpecObject.
- bib.al.original-language: en
- bib.dp.publication-date: 2025-03-01
- ids.document: 99200
- ids.element: o1749224057377-sub-9.4.5.2
- ids.language-synoptic: o1749224057377-sub-9.4.5.2
- ids.tracing: hash-463888f18d7bb8e352adb41b8c4f08c34375345ef834e00803d18ec5bbcd4ea2
- obj.clause-number: 9.4.5.2
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

###### tr--6d400e6f-d82a-44a1-8922-1185ec080fbf--AgbhV3Ez0EPg: Each item of an enumeration as a separate provision (provision)
The context of the enumeration should be retained as a relationship to a parent container SpecObject.
- bib.al.original-language: en
- bib.dp.publication-date: 2025-03-01
- ids.document: 99200
- ids.element: o1749224057377-sub-9.4.5.2
- ids.language-synoptic: o1749224057377-sub-9.4.5.2
- ids.tracing: hash-8cf96856792b1b0cd0b0aebfd62e3d48eeab2e68869fa1eb37c01976473a803c
- obj.clause-number: 9.4.5.2
- obj.element-name: paragraph
- obj.language: en
- obj.modality: recommendation
- obj.normativity: normative
- obj.specobject-type: provision
- use.business-process: undefined
- use.business-sector: undefined
- use.interaction: undefined
- use.location: undefined
- use.product-category: undefined
- use.product-life-cycle: undefined
- use.project-phase: undefined
- use.purpose: undefined

###### tr--6d400e6f-d82a-44a1-8922-1185ec080fbf--N9y8wUA90stc: Each item of an enumeration as a separate provision (provision)
If criteria for both methods are met, the first method has priority, and the whole enumeration should be handled as one SpecObject (see 9.4.5.1).
- bib.al.original-language: en
- bib.dp.publication-date: 2025-03-01
- ids.document: 99200
- ids.element: o1749224057377-sub-9.4.5.2
- ids.language-synoptic: o1749224057377-sub-9.4.5.2
- ids.tracing: hash-eec930ec40a72eb86473faa98bcce6326d1da9e6c117390ce71a1e1a9b5baeca
- obj.clause-number: 9.4.5.2
- obj.element-name: paragraph
- obj.language: en
- obj.modality: recommendation
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-a2ed100a4155469

###### prov-100000012-e758a00f5b2144f: Each item of an enumeration as a separate provision (provision)
EXAMPLE:
Each item of an enumeration is a separate provision:
“The test procedure shall be performed as follows:
- a)
a) The user shall switch on the device.
- b)
b) The user shall insert the test object.
- c)
c) The user shall press the start button.
- d)
d) The user shall document the test results.
- e)
e) The user shall remove the test object.
- f)
f) The user shall switch off the device.”
- bib.al.original-language: en
- bib.dp.publication-date: 2025-03-01
- ids.document: 99200
- ids.element: o1749224057377-sub-9.4.5.2
- ids.language-synoptic: o1749224057377-sub-9.4.5.2
- ids.tracing: hash-55deda4f9c136e71120b2273df5d606024d34ee264252605352b3320fd929cb0
- obj.clause-number: 9.4.5.2
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### prov-100000012-f6b372b6c56a41b: Modality; bindingness (heading)
- bib.al.original-language: en
- bib.dp.publication-date: 2025-03-01
- ids.document: 99200
- ids.element: o1749224057380-sub-9.5
- ids.language-synoptic: o1749224057380-sub-9.5
- ids.tracing: hash-94710aafa7b987e3cc2344ebf24cec9ee2661f1224c5f39f0e1b53b14d9549e6
- obj.clause-number: 9.5
- obj.element-name: heading
- obj.language: en
- obj.specobject-type: heading
- ChapterName: 9.5 Modality; bindingness

#### prov-100000012-33c57f63ec70422: Determining the modality (obj.modality) (heading)
- bib.al.original-language: en
- bib.dp.publication-date: 2025-03-01
- ids.document: 99200
- ids.element: o1749224057382-sub-9.5.1
- ids.language-synoptic: o1749224057382-sub-9.5.1
- ids.tracing: hash-bb3a8798fbda055df46c80d149ec6112bfdba077ae4be06060838e807f2de7a1
- obj.clause-number: 9.5.1
- obj.element-name: heading
- obj.language: en
- obj.specobject-type: heading
- ChapterName: 9.5.1 Determining the modality (obj.modality)

##### tr--6d400e6f-d82a-44a1-8922-1185ec080fbf--wAjK9Ipzy5yw: Determining the modality (obj.modality) (provision)
The values of the attribute obj.modality (8.2.1.2) shall be determined for each sentence of the public standard (see 9.2.1).
- bib.al.original-language: en
- bib.dp.publication-date: 2025-03-01
- ids.document: 99200
- ids.element: o1749224057382-sub-9.5.1
- ids.language-synoptic: o1749224057382-sub-9.5.1
- ids.tracing: hash-e8bec479e6242f42abe703e324ab288e5433c90384d33cdc060bc10af399f079
- obj.clause-number: 9.5.1
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-2f90c5903f8d49c
- cross-reference -> prov-100000012-379fbd391ce7432

##### tr--6d400e6f-d82a-44a1-8922-1185ec080fbf--BTBcgTLMPqHE: Determining the modality (obj.modality) (provision)
Depending on the selected level of fragmentation (see 9.2.1) of the public standard, the resulting values of the attribute obj.modality (8.2.1.2) of the SpecObject shall be determined according to 9.5.2.
- bib.al.original-language: en
- bib.dp.publication-date: 2025-03-01
- ids.document: 99200
- ids.element: o1749224057382-sub-9.5.1
- ids.language-synoptic: o1749224057382-sub-9.5.1
- ids.tracing: hash-511c246bf277aac2a33e60dd485a88278b7087e0843e02186bf732549317ac62
- obj.clause-number: 9.5.1
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-379fbd391ce7432
- cross-reference -> prov-100000012-2f90c5903f8d49c
- cross-reference -> prov-100000012-213d36a6587f48e

##### tr--6d400e6f-d82a-44a1-8922-1185ec080fbf--N1LZqtIm2wqf: Determining the modality (obj.modality) (provision)
The values of the attribute obj.modality (8.2.1.2) shall be selected from 8.3.3 according to the ISO/IEC Directives, Part 2.
- bib.al.original-language: en
- bib.dp.publication-date: 2025-03-01
- ids.document: 99200
- ids.element: o1749224057382-sub-9.5.1
- ids.language-synoptic: o1749224057382-sub-9.5.1
- ids.tracing: hash-b7a64786f2606561f0e11562a2b7c00905f3c087a9478bb459c31d1ebace204b
- obj.clause-number: 9.5.1
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-2f90c5903f8d49c
- cross-reference -> prov-100000012-24f804847435467

##### tr--6d400e6f-d82a-44a1-8922-1185ec080fbf--eHOLi8DnM1OH: Determining the modality (obj.modality) (provision)
If the values of the attribute obj.modality (8.2.1.2) has been determined using natural language processing, the attribute obj.modality (8.2.1.2) shall be set to a value according to 8.3.3:
- If the actual fragment contains two or more different modalities, the modality shall be interpreted as the value “ambiguous”.
- If the actual fragment contains the modality for a capability or possibility, the modality may be assumed as the value “possibility”.
- If the actual fragment contains the modality for an external constraint or a requirement, the modality may be assumed as the value “requirement”.
- If no modality could be determined for the actual fragment, the modality shall be interpreted as the value “undefined” (equivalent to “statement” according to the ISO/IEC Directives, Part 2).
- bib.al.original-language: en
- bib.dp.publication-date: 2025-03-01
- ids.document: 99200
- ids.element: o1749224057382-sub-9.5.1
- ids.language-synoptic: o1749224057382-sub-9.5.1
- ids.tracing: hash-f681a233ec05ef46e0762c379d15090f60c300358d79a9c56fc720f607a8944e
- obj.clause-number: 9.5.1
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-2f90c5903f8d49c
- cross-reference -> prov-100000012-24f804847435467

##### prov-100000012-eca220ee468b403: Determining the modality (obj.modality), Note (provision)
NOTE:
Although an external constrains is formally not a modality, the obj.modality (8.2.1.2) contains the value “constraint” since the attribute represents not only modalities but all levels of obligations for the user.
- bib.al.original-language: en
- bib.dp.publication-date: 2025-03-01
- ids.document: 99200
- ids.element: o1749224057382-sub-9.5.1
- ids.language-synoptic: o1749224057382-sub-9.5.1
- ids.tracing: hash-a18f1a39405f11d42537434e5784be85d07b076997a6c63177502a7da4e9cf61
- obj.clause-number: 9.5.1
- obj.element-name: note
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
- cross-reference -> prov-100000012-2f90c5903f8d49c

#### prov-100000012-213d36a6587f48e: Modalities related to context (heading)
- bib.al.original-language: en
- bib.dp.publication-date: 2025-03-01
- ids.document: 99200
- ids.element: o1749224057384-sub-9.5.2
- ids.language-synoptic: o1749224057384-sub-9.5.2
- ids.tracing: hash-2ded0b19c3745504ee79b7237ae1ae8574caf5f3d86583248a393ab9e97ed33b
- obj.clause-number: 9.5.2
- obj.element-name: heading
- obj.language: en
- obj.specobject-type: heading
- ChapterName: 9.5.2 Modalities related to context

##### prov-100000012-65cb6aae82b54bb: Modalities related to context (provision)
- To classify sentences, the attribute obj.modality (8.2.1.2) shall be set to the value determined for the sentence.
- To classify paragraphs, the attribute obj.modality (8.2.1.2) shall be set to the value for the highest bindingness (see 9.5.3) of the sentences contained in the paragraph.
- To classify divisions, the attribute obj.modality (8.2.1.2) shall be set to the value for the highest bindingness (see 9.5.3) of the sentences contained in the division.
- bib.al.original-language: en
- bib.dp.publication-date: 2025-03-01
- ids.document: 99200
- ids.element: o1749224057384-sub-9.5.2
- ids.language-synoptic: o1749224057384-sub-9.5.2
- ids.tracing: hash-227d08306df7d7221aa6832ee5e2393c744b1d1c70b85b94332163333ef01ab3
- obj.clause-number: 9.5.2
- obj.element-name: unordered-list
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-2f90c5903f8d49c
- cross-reference -> prov-100000012-ee2d437639b449d

##### prov-100000012-c87819386678454: Modalities related to context (provision)
EXAMPLE:
- If a paragraph contains several sentences using the division-wise output (see 9.4.1.1), the sentence with the highest bindingness determines the modality of the SpecObject. This means that if the division contains at least one requirement, the whole division shall be classified as a requirement.
- If a paragraph contains several sentences using a paragraph-wise output (see 9.4.1.2), the sentence with the highest binding determines the modality of the SpecObject. This means that if the paragraph contains at least one requirement, the whole paragraph shall be classified as a requirement.
- If a sentence is one of more sentences of an atomic element (see 9.4.3) using the standard sentence-wise output (see 9.4.1.3), the sentence with the highest bindingness determines the modality of the SpecObject. This means that if the element contains at least one requirement, the whole element shall be classified as a requirement.
- bib.al.original-language: en
- bib.dp.publication-date: 2025-03-01
- ids.document: 99200
- ids.element: o1749224057384-sub-9.5.2
- ids.language-synoptic: o1749224057384-sub-9.5.2
- ids.tracing: hash-7bb5a07cfde20d3037123100632e48c1338706e7660fcf2adf8a528dd3a84714
- obj.clause-number: 9.5.2
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
- cross-reference -> prov-100000012-f6c75a9523fc4a5
- cross-reference -> prov-100000012-5e01855e805a424
- cross-reference -> prov-100000012-6c210d928624496
- cross-reference -> prov-100000012-0a1f4dc8db3c4a2

#### prov-100000012-ee2d437639b449d: Bindingness of the modality values (heading)
- bib.al.original-language: en
- bib.dp.publication-date: 2025-03-01
- ids.document: 99200
- ids.element: o1749224057386-sub-9.5.3
- ids.language-synoptic: o1749224057386-sub-9.5.3
- ids.tracing: hash-5d658a770c436c2009d16b289528a424a479cead211c5407f975d3352b941c06
- obj.clause-number: 9.5.3
- obj.element-name: heading
- obj.language: en
- obj.specobject-type: heading
- ChapterName: 9.5.3 Bindingness of the modality values

##### tr--6d400e6f-d82a-44a1-8922-1185ec080fbf--WFAPhwDd5TCF: Bindingness of the modality values (provision)
The values of the attribute obj.modality (8.2.1.2) are listed from the highest (1) to the lowest (9) bindingness:
1. constraint;
2. requirement;
3. recommendation;
4. capability;
5. permission;
6. possibility;
7. ambiguous;
8. undefined (statement);
9. value for the attribute has not been determined.
- bib.al.original-language: en
- bib.dp.publication-date: 2025-03-01
- ids.document: 99200
- ids.element: o1749224057386-sub-9.5.3
- ids.language-synoptic: o1749224057386-sub-9.5.3
- ids.tracing: hash-a66236ef5cb958ef758f34ffe07ee60040326dd059cd785d028cee72369a8dfb
- obj.clause-number: 9.5.3
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-2f90c5903f8d49c

#### prov-100000012-bb04960b02274d2: Review of the modality (obj.modality) (heading)
- bib.al.original-language: en
- bib.dp.publication-date: 2025-03-01
- ids.document: 99200
- ids.element: o1749224057388-sub-9.5.4
- ids.language-synoptic: o1749224057388-sub-9.5.4
- ids.tracing: hash-d005c1cb12c836e8b6cef2b20c8a2730485c45844e640ee41d33a8d5ab216aba
- obj.clause-number: 9.5.4
- obj.element-name: heading
- obj.language: en
- obj.specobject-type: heading
- ChapterName: 9.5.4 Review of the modality (obj.modality)

##### prov-100000012-e2845fda2652450: Review of the modality (obj.modality) (provision)
- If the attribute obj.modality (8.2.1.2) has been determined using natural language processing, the user shall validate ambiguous and uncertain values during the review of the ReqIF™ (see 9.5.5).
- If the attribute obj.modality (8.2.1.2) has been determined using natural language processing, the supplier should support the user review with additional information about the reliability of the recognized modality for each SpecObject in the ReqIF™ file (see 9.7.3).
- bib.al.original-language: en
- bib.dp.publication-date: 2025-03-01
- ids.document: 99200
- ids.element: o1749224057388-sub-9.5.4
- ids.language-synoptic: o1749224057388-sub-9.5.4
- ids.tracing: hash-72b0ad06aa006d6e2430ffd0bc82b6786fdd19d9412af8b20c7939b13dd5d709
- obj.clause-number: 9.5.4
- obj.element-name: unordered-list
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-2f90c5903f8d49c
- cross-reference -> prov-100000012-bdc9b1b07ef6407
- cross-reference -> prov-100000012-86bb27fe02cc4de

##### tr--6d400e6f-d82a-44a1-8922-1185ec080fbf--T1Rjy0pS1nMC: Review of the modality (obj.modality) (provision)
Since users may not blindly rely on automatically determined results from post-processing services, the user is responsible to review each SpecObject in the ReqIF™ file which is the result of such post-processing.
- bib.al.original-language: en
- bib.dp.publication-date: 2025-03-01
- ids.document: 99200
- ids.element: o1749224057388-sub-9.5.4
- ids.language-synoptic: o1749224057388-sub-9.5.4
- ids.tracing: hash-17b78058f9d33bb8f30317df58dcb4ff1149a5bf4a73408c18205e6f04dbc447
- obj.clause-number: 9.5.4
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### tr--6d400e6f-d82a-44a1-8922-1185ec080fbf--5TngiZAvRuez: Review of the modality (obj.modality) (provision)
If the service deliverable has been confirmed by the authority responsible for the public standard, users may assume a high reliability of a service.
- bib.al.original-language: en
- bib.dp.publication-date: 2025-03-01
- ids.document: 99200
- ids.element: o1749224057388-sub-9.5.4
- ids.language-synoptic: o1749224057388-sub-9.5.4
- ids.tracing: hash-d17a2fb441b9c766f11338398cf333f0ea0f80cc95140c8de39bd399668fe0a7
- obj.clause-number: 9.5.4
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-100000012-bdc9b1b07ef6407: Align the modality (obj.modality) (heading)
- bib.al.original-language: en
- bib.dp.publication-date: 2025-03-01
- ids.document: 99200
- ids.element: o1749224057390-sub-9.5.5
- ids.language-synoptic: o1749224057390-sub-9.5.5
- ids.tracing: hash-a440dbcae13c50c92d5162be6c57732dda5af5d9d3234722c9058016eac7bc7a
- obj.clause-number: 9.5.5
- obj.element-name: heading
- obj.language: en
- obj.specobject-type: heading
- ChapterName: 9.5.5 Align the modality (obj.modality)

##### prov-100000012-b6e0dafa2159444: Align the modality (obj.modality) (provision)
- If capabilities and possibilities are required differentiated, the user shall align the attribute obj.modality (8.2.1.2) to the according value (see 8.3.3).
- If external constraints and requirements are required differentiated, the user shall align the attribute obj.modality (8.2.1.2) to the according value (see 8.3.3).
- If modality is ambiguous, missing or undefined, the user shall align the attribute obj.modality (8.2.1.2) to the according value (see 8.3.3).
- bib.al.original-language: en
- bib.dp.publication-date: 2025-03-01
- ids.document: 99200
- ids.element: o1749224057390-sub-9.5.5
- ids.language-synoptic: o1749224057390-sub-9.5.5
- ids.tracing: hash-45f5c26c6ff1fa3e2333fb0e51616005be9f25fa61fa1958a81b97688e4f5c26
- obj.clause-number: 9.5.5
- obj.element-name: unordered-list
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-2f90c5903f8d49c
- cross-reference -> prov-100000012-24f804847435467

### prov-100000012-ffcbbe0b3d36446: Content attributes (ReqIF.*) (heading)
- bib.al.original-language: en
- bib.dp.publication-date: 2025-03-01
- ids.document: 99200
- ids.element: o1749224057393-sub-9.6
- ids.language-synoptic: o1749224057393-sub-9.6
- ids.tracing: hash-2d2286d65647fc6321ec7499a1801e6731108f81ebc5fa7cbf58ddea75f028a1
- obj.clause-number: 9.6
- obj.element-name: heading
- obj.language: en
- obj.specobject-type: heading
- ChapterName: 9.6 Content attributes (ReqIF.*)

#### prov-100000012-18bc1f195ab945a: Heading (ReqIF.ChapterName) (heading)
- bib.al.original-language: en
- bib.dp.publication-date: 2025-03-01
- ids.document: 99200
- ids.element: o1749224057395-sub-9.6.1
- ids.language-synoptic: o1749224057395-sub-9.6.1
- ids.tracing: hash-a37a2fecb5317261ed6fba86a70b8e8f22c6a7f84716f27cef3ea59bb7683537
- obj.clause-number: 9.6.1
- obj.element-name: heading
- obj.language: en
- obj.specobject-type: heading
- ChapterName: 9.6.1 Heading (ReqIF.ChapterName)

##### tr--6d400e6f-d82a-44a1-8922-1185ec080fbf--3r5Zxn9c60Hg: Heading (ReqIF.ChapterName) (provision)
The heading of the SpecObject shall be output as value of the attribute ReqIF.ChapterName (9.6.1) according to 9.1.
- bib.al.original-language: en
- bib.dp.publication-date: 2025-03-01
- ids.document: 99200
- ids.element: o1749224057395-sub-9.6.1
- ids.language-synoptic: o1749224057395-sub-9.6.1
- ids.tracing: hash-df00a8b9f520ea25641e63cd24c54f8b4413072a5248d3b494558c4c9d754414
- obj.clause-number: 9.6.1
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-18bc1f195ab945a
- cross-reference -> prov-100000012-285e0301396b48d

##### tr--6d400e6f-d82a-44a1-8922-1185ec080fbf--NQPgn7XbqRCR: Heading (ReqIF.ChapterName) (provision)
If given in the source document, the original labelling and numbering of the public standard shall be output according to 10.2.
- bib.al.original-language: en
- bib.dp.publication-date: 2025-03-01
- ids.document: 99200
- ids.element: o1749224057395-sub-9.6.1
- ids.language-synoptic: o1749224057395-sub-9.6.1
- ids.tracing: hash-e8669bf886c2958e17effa4cf0e62ff634278a53bfd4deac109263959eecfd80
- obj.clause-number: 9.6.1
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-9af61d186e40429

##### tr--6d400e6f-d82a-44a1-8922-1185ec080fbf--kNc7qaCjTjCy: Heading (ReqIF.ChapterName) (provision)
If the value of ReqIF.ChapterName (9.6.1) shall be set, the value of ReqIF.Text (9.6.2) shall not be set.
- bib.al.original-language: en
- bib.dp.publication-date: 2025-03-01
- ids.document: 99200
- ids.element: o1749224057395-sub-9.6.1
- ids.language-synoptic: o1749224057395-sub-9.6.1
- ids.tracing: hash-0525eee15a86b04f684473b2c24bb0a3086c3e7b0d892b3d7d0fd9551a94a9ae
- obj.clause-number: 9.6.1
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-18bc1f195ab945a
- cross-reference -> prov-100000012-ed8a82f3f64d4bb

##### prov-100000012-dfd2cd3c208240c: Heading (ReqIF.ChapterName) (provision)
EXAMPLE:
Output for the heading of the clause “1 Scope”:
- ReqIF.ChapterName: “1 Scope”;
- ReqIF.Text: not set;
- obj.clause-heading: “Scope”;
- obj.clause-number: “1”.
- bib.al.original-language: en
- bib.dp.publication-date: 2025-03-01
- ids.document: 99200
- ids.element: o1749224057395-sub-9.6.1
- ids.language-synoptic: o1749224057395-sub-9.6.1
- ids.tracing: hash-d0a273b1d37dbf9209aaa66287883bea5d0e8d2aa2a2fba96ee75484f4139593
- obj.clause-number: 9.6.1
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

#### prov-100000012-ed8a82f3f64d4bb: Content (ReqIF.Text) (heading)
- bib.al.original-language: en
- bib.dp.publication-date: 2025-03-01
- ids.document: 99200
- ids.element: o1749224057397-sub-9.6.2
- ids.language-synoptic: o1749224057397-sub-9.6.2
- ids.tracing: hash-85854de7f8656f90945c43e6a554c5ff3f53d2f23f346ab5b2274685c958e097
- obj.clause-number: 9.6.2
- obj.element-name: heading
- obj.language: en
- obj.specobject-type: heading
- ChapterName: 9.6.2 Content (ReqIF.Text)

##### tr--6d400e6f-d82a-44a1-8922-1185ec080fbf--T0uvDobpzFMD: Content (ReqIF.Text) (provision)
The content of the SpecObject shall be output as value of the attribute ReqIF.Text (9.6.2).
- bib.al.original-language: en
- bib.dp.publication-date: 2025-03-01
- ids.document: 99200
- ids.element: o1749224057397-sub-9.6.2
- ids.language-synoptic: o1749224057397-sub-9.6.2
- ids.tracing: hash-4e926a493b3cae11fae023fadd265bebe845da729c5f382225e6362f12ef7f38
- obj.clause-number: 9.6.2
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-ed8a82f3f64d4bb

##### tr--6d400e6f-d82a-44a1-8922-1185ec080fbf--VX1ZpMas0tbZ: Content (ReqIF.Text) (provision)
If given in the source document, the original labelling and numbering of the public standard shall be output according to 10.2.
- bib.al.original-language: en
- bib.dp.publication-date: 2025-03-01
- ids.document: 99200
- ids.element: o1749224057397-sub-9.6.2
- ids.language-synoptic: o1749224057397-sub-9.6.2
- ids.tracing: hash-710f9baf2fcd575f788ca9a7ea03027b4eadd23f4f6d5b104dbaf18edcf68b45
- obj.clause-number: 9.6.2
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-9af61d186e40429

##### tr--6d400e6f-d82a-44a1-8922-1185ec080fbf--7AdzkAbYmeNI: Content (ReqIF.Text) (provision)
If the value of ReqIF.Text (9.6.2) shall be set, the value of ReqIF.ChapterName (9.6.1) shall not be set.
- bib.al.original-language: en
- bib.dp.publication-date: 2025-03-01
- ids.document: 99200
- ids.element: o1749224057397-sub-9.6.2
- ids.language-synoptic: o1749224057397-sub-9.6.2
- ids.tracing: hash-16d7d6573fd332e5bcce38655d341e77ad0b08393a4d75e5aef6a3b2920ddc86
- obj.clause-number: 9.6.2
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-ed8a82f3f64d4bb
- cross-reference -> prov-100000012-18bc1f195ab945a

##### prov-100000012-9b95db1b1db14ef: Content (ReqIF.Text) (provision)
EXAMPLE:
Output for the element “WARNING: This mixture can be explosively unstable, particularly if heated.” specified within Annex B “Some typical etchants for use at room temperature”:
- ReqIF.ChapterName: not set;
- ReqIF.Text: “WARNING: This mixture can be explosively unstable, particularly if heated.”.
- bib.al.original-language: en
- bib.dp.publication-date: 2025-03-01
- ids.document: 99200
- ids.element: o1749224057397-sub-9.6.2
- ids.language-synoptic: o1749224057397-sub-9.6.2
- ids.tracing: hash-6e90158bfb7e6406d067472d349bfd9a9023458597ed1e6c67aa358c64f4abf2
- obj.clause-number: 9.6.2
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
- cross-reference -> prov-100000012-89ac3171bcc648d

### prov-100000012-c7e10059bbec4ec: Object attributes (obj.*) (heading)
- bib.al.original-language: en
- bib.dp.publication-date: 2025-03-01
- ids.document: 99200
- ids.element: o1749224057400-sub-9.7
- ids.language-synoptic: o1749224057400-sub-9.7
- ids.tracing: hash-b5ab4b5a5b870887e7289c406f07da0dbf3a72f35558906e71397b774a5bfad7
- obj.clause-number: 9.7
- obj.element-name: heading
- obj.language: en
- obj.specobject-type: heading
- ChapterName: 9.7 Object attributes (obj.*)

#### prov-100000012-29c2913e2b8e496: Clause heading (obj.clause-heading) (heading)
- bib.al.original-language: en
- bib.dp.publication-date: 2025-03-01
- ids.document: 99200
- ids.element: o1749224057402-sub-9.7.1
- ids.language-synoptic: o1749224057402-sub-9.7.1
- ids.tracing: hash-7bd2f0b2efdfcd7e0b9e0ce73d69f52db5365fb0c02b5382e7338b86031cf0e1
- obj.clause-number: 9.7.1
- obj.element-name: heading
- obj.language: en
- obj.specobject-type: heading
- ChapterName: 9.7.1 Clause heading (obj.clause-heading)

##### tr--6d400e6f-d82a-44a1-8922-1185ec080fbf--o2bBblYqm3Yt: Clause heading (obj.clause-heading) (provision)
If given in the source document, the original heading of the parent division in the public standard shall be output as value of the attribute obj.clause-heading (8.2.1.2) according to 9.1.
- bib.al.original-language: en
- bib.dp.publication-date: 2025-03-01
- ids.document: 99200
- ids.element: o1749224057402-sub-9.7.1
- ids.language-synoptic: o1749224057402-sub-9.7.1
- ids.tracing: hash-2bf37f31ea04da9f50263b8fef66173b3d9ce8fbfac08cce1e8787c49e6a3a48
- obj.clause-number: 9.7.1
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-2f90c5903f8d49c
- cross-reference -> prov-100000012-285e0301396b48d

##### prov-100000012-41bb6e7d4e4c4ab: Clause heading (obj.clause-heading) (provision)
EXAMPLE 1:
Output for the heading of the clause “1 Scope”:
- obj.clause-heading: “Scope”;
- obj.clause-number: “1”.
- bib.al.original-language: en
- bib.dp.publication-date: 2025-03-01
- ids.document: 99200
- ids.element: o1749224057402-sub-9.7.1
- ids.language-synoptic: o1749224057402-sub-9.7.1
- ids.tracing: hash-728e40d4cb5794a7711a1db88bf2c23e467dd80d10748fbe8fae56872b207a4e
- obj.clause-number: 9.7.1
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

##### prov-100000012-735f480c74724b7: Clause heading (obj.clause-heading) (provision)
EXAMPLE 2:
Output for the element “WARNING: This mixture can be explosively unstable, particularly if heated.” specified within Annex B “Some typical etchants for use at room temperature”:
- obj.clause-heading: “Some typical etchants for use at room temperature”;
- obj.clause-number: “Annex B”.
- bib.al.original-language: en
- bib.dp.publication-date: 2025-03-01
- ids.document: 99200
- ids.element: o1749224057402-sub-9.7.1
- ids.language-synoptic: o1749224057402-sub-9.7.1
- ids.tracing: hash-7ef3c9ae7cde87201fc9d0e3e9b3bf70fde345e5eab05e7f923c6291246b3812
- obj.clause-number: 9.7.1
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
- cross-reference -> prov-100000012-89ac3171bcc648d

#### prov-100000012-88079988895141e: Clause context (obj.clause-number) (heading)
- bib.al.original-language: en
- bib.dp.publication-date: 2025-03-01
- ids.document: 99200
- ids.element: o1749224057404-sub-9.7.2
- ids.language-synoptic: o1749224057404-sub-9.7.2
- ids.tracing: hash-ec9f3478529cb7a47293982f707065c301882ff3fbd6cedbd6ae2c81828746cc
- obj.clause-number: 9.7.2
- obj.element-name: heading
- obj.language: en
- obj.specobject-type: heading
- ChapterName: 9.7.2 Clause context (obj.clause-number)

##### tr--6d400e6f-d82a-44a1-8922-1185ec080fbf--gqeo8cT0wVPB: Clause context (obj.clause-number) (provision)
If given in the source document, the original labelling and numbering of the parent division in the public standard shall be output as value of the attribute obj.clause-number (8.2.1.2) according to 9.1.
- bib.al.original-language: en
- bib.dp.publication-date: 2025-03-01
- ids.document: 99200
- ids.element: o1749224057404-sub-9.7.2
- ids.language-synoptic: o1749224057404-sub-9.7.2
- ids.tracing: hash-032a38ce36909b6182f4062b6904d0f24547d64f7301023537d1aaf05e2d9a15
- obj.clause-number: 9.7.2
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-2f90c5903f8d49c
- cross-reference -> prov-100000012-285e0301396b48d

##### prov-100000012-3ba767a48f484b2: Clause context (obj.clause-number) (provision)
EXAMPLE 1:
Output for the heading of the clause “1 Scope”:
- obj.clause-heading: “Scope”;
- obj.clause-number: “1”.
- bib.al.original-language: en
- bib.dp.publication-date: 2025-03-01
- ids.document: 99200
- ids.element: o1749224057404-sub-9.7.2
- ids.language-synoptic: o1749224057404-sub-9.7.2
- ids.tracing: hash-33a6cf55a58117444b104294cd03e0cc58586cdd58735e6cff8d02ef2da53810
- obj.clause-number: 9.7.2
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

##### prov-100000012-6aaf0ec2390d48a: Clause context (obj.clause-number) (provision)
EXAMPLE 2:
Output for the element “WARNING: This mixture can be explosively unstable, particularly if heated.” specified within Annex B “Some typical etchants for use at room temperature”:
- obj.clause-heading: “Some typical etchants for use at room temperature”;
- obj.clause-number: “Annex B”.
- bib.al.original-language: en
- bib.dp.publication-date: 2025-03-01
- ids.document: 99200
- ids.element: o1749224057404-sub-9.7.2
- ids.language-synoptic: o1749224057404-sub-9.7.2
- ids.tracing: hash-34e3f816a29b47c86b6a68c773fb3d15669a344b69ba992fcf9aff8edd171b17
- obj.clause-number: 9.7.2
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
- cross-reference -> prov-100000012-89ac3171bcc648d

#### prov-100000012-86bb27fe02cc4de: Reliability (obj.conversion-reliability) (heading)
- bib.al.original-language: en
- bib.dp.publication-date: 2025-03-01
- ids.document: 99200
- ids.element: o1749224057407-sub-9.7.3
- ids.language-synoptic: o1749224057407-sub-9.7.3
- ids.tracing: hash-6f92bc86418fb4e0fd93fa37c9d4131e20c0284ad14598723ac4b0eef8577d7a
- obj.clause-number: 9.7.3
- obj.element-name: heading
- obj.language: en
- obj.specobject-type: heading
- ChapterName: 9.7.3 Reliability (obj.conversion-reliability)

##### prov-100000012-019577e55d4144f: Determining the reliability (heading)
- bib.al.original-language: en
- bib.dp.publication-date: 2025-03-01
- ids.document: 99200
- ids.element: o1749224057409-sub-9.7.3.1
- ids.language-synoptic: o1749224057409-sub-9.7.3.1
- ids.tracing: hash-b49df9981395f5187134c98317614c400b90116a2144f828abe5632ea93cf592
- obj.clause-number: 9.7.3.1
- obj.element-name: heading
- obj.language: en
- obj.specobject-type: heading
- ChapterName: 9.7.3.1 Determining the reliability

###### prov-100000012-f5d4f608c49b491: Determining the reliability (provision)
- If the attribute obj.modality (8.2.1.2) has been confirmed by the authority responsible for the public standard, the supplier shall set the obj.conversion-reliability (8.2.1.2) for each SpecObject in the ReqIF™ file to the value “100” (%).
- If the attribute obj.modality (8.2.1.2) has been determined using natural language processing, the supplier may set the attribute obj.conversion-reliability (8.2.1.2) for each SpecObject in the ReqIF™ file to the value between “0” and “99” (%).
- If the attribute obj.modality (8.2.1.2) has not been assessed, the supplier shall not set the attribute obj.conversion-reliability (8.2.1.2) for the respective SpecObjects in the ReqIF™.
- bib.al.original-language: en
- bib.dp.publication-date: 2025-03-01
- ids.document: 99200
- ids.element: o1749224057409-sub-9.7.3.1
- ids.language-synoptic: o1749224057409-sub-9.7.3.1
- ids.tracing: hash-9950a1051fae4499d21bee06f44fbca3e73e5187fc330e82efb1b0b02a52c080
- obj.clause-number: 9.7.3.1
- obj.element-name: unordered-list
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-2f90c5903f8d49c

###### tr--6d400e6f-d82a-44a1-8922-1185ec080fbf--OXgBbbTwHZ8s: Determining the reliability (provision)
The users may assume:
- If the attribute obj.conversion-reliability (8.2.1.2) has the value “100”, the supplier expresses that the originator as the authority responsible for the public standard has confirmed the value of the attribute obj.modality (8.2.1.2).
- If the attribute obj.conversion-reliability (8.2.1.2) has the value “0”, the supplier has determined the lowest possible conversion reliability.
- If the attribute obj.conversion-reliability (8.2.1.2) has not been set, the supplier expresses no statement about the conversion reliability.
- bib.al.original-language: en
- bib.dp.publication-date: 2025-03-01
- ids.document: 99200
- ids.element: o1749224057409-sub-9.7.3.1
- ids.language-synoptic: o1749224057409-sub-9.7.3.1
- ids.tracing: hash-f9c064f7f1503c4182074c254db89f1c9ea625319e8748ae3ec7d2d5704b6e68
- obj.clause-number: 9.7.3.1
- obj.element-name: paragraph
- obj.language: en
- obj.modality: permission
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-2f90c5903f8d49c

###### prov-100000012-6efd4681a204483: Determining the reliability, Note (provision)
NOTE:
Annex D contains typical criteria for the quality of provisions which can be used to determine a value for the attribute obj.conversion-reliability (8.2.1.2).
- bib.al.original-language: en
- bib.dp.publication-date: 2025-03-01
- ids.document: 99200
- ids.element: o1749224057409-sub-9.7.3.1
- ids.language-synoptic: o1749224057409-sub-9.7.3.1
- ids.tracing: hash-34e745004f2f10055889326895a283a4dfc1e4185357128933043b42463bd0bd
- obj.clause-number: 9.7.3.1
- obj.element-name: note
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
- cross-reference -> prov-100000012-c726f394be984a9
- cross-reference -> prov-100000012-2f90c5903f8d49c

##### prov-100000012-ab4f157ccf3e4d9: Using the reliability (heading)
- bib.al.original-language: en
- bib.dp.publication-date: 2025-03-01
- ids.document: 99200
- ids.element: o1749224057411-sub-9.7.3.2
- ids.language-synoptic: o1749224057411-sub-9.7.3.2
- ids.tracing: hash-6dc2bd703da094de3d2916c6205fbfed19ebf2dd2dafe002d333af4ecda5a669
- obj.clause-number: 9.7.3.2
- obj.element-name: heading
- obj.language: en
- obj.specobject-type: heading
- ChapterName: 9.7.3.2 Using the reliability

###### tr--6d400e6f-d82a-44a1-8922-1185ec080fbf--AhdzEQQv6I5O: Using the reliability (provision)
If the attribute obj.conversion-reliability (8.2.1.2) has been set for the respective SpecObject, the users can filter or sort the values to focus or prioritize the review of all SpecObjects in the ReqIF™.
- bib.al.original-language: en
- bib.dp.publication-date: 2025-03-01
- ids.document: 99200
- ids.element: o1749224057411-sub-9.7.3.2
- ids.language-synoptic: o1749224057411-sub-9.7.3.2
- ids.tracing: hash-3eb0a149323ef5cce8f4160561bed8715a94ae02d3349c798e5ff1984f6ab064
- obj.clause-number: 9.7.3.2
- obj.element-name: paragraph
- obj.language: en
- obj.modality: permission
- obj.normativity: normative
- obj.specobject-type: provision
- obj.transformation-issues: Possibly wrong modal verb
- use.business-process: undefined
- use.business-sector: undefined
- use.interaction: undefined
- use.location: undefined
- use.product-category: undefined
- use.product-life-cycle: undefined
- use.project-phase: undefined
- use.purpose: undefined
- cross-reference -> prov-100000012-2f90c5903f8d49c

###### prov-100000012-64281ee055da429: Using the reliability (provision)
EXAMPLE:
If all SpecObjects are sorted from the value “0” up to “99” (%), the users can review the SpecObjects beginning with the least estimated reliability up to the highest estimated reliability.
- bib.al.original-language: en
- bib.dp.publication-date: 2025-03-01
- ids.document: 99200
- ids.element: o1749224057411-sub-9.7.3.2
- ids.language-synoptic: o1749224057411-sub-9.7.3.2
- ids.tracing: hash-dc85c0dac4505af422e5bead9924e37d19150a6651ca4ba091c427542dc25233
- obj.clause-number: 9.7.3.2
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

#### prov-100000012-89851edad11f4e1: Standard element (obj.element-name) (heading)
- bib.al.original-language: en
- bib.dp.publication-date: 2025-03-01
- ids.document: 99200
- ids.element: o1749224057413-sub-9.7.4
- ids.language-synoptic: o1749224057413-sub-9.7.4
- ids.tracing: hash-2d270061f4eab4d2ddb97ae8eea3e8296cd5a20cd7cb5f6a152c94d166686c30
- obj.clause-number: 9.7.4
- obj.element-name: heading
- obj.language: en
- obj.specobject-type: heading
- ChapterName: 9.7.4 Standard element (obj.element-name)

##### prov-100000012-d4f1ac8a46c440a: Standard element (obj.element-name) (provision)
- If the source document is an XML instance, the parent block element shall be output using the corresponding value of the attribute obj.clause-heading (8.2.1.2) according to 9.1.
- If the source document is not an XML instance, the attribute obj.clause-heading (8.2.1.2) shall not be set.
- bib.al.original-language: en
- bib.dp.publication-date: 2025-03-01
- ids.document: 99200
- ids.element: o1749224057413-sub-9.7.4
- ids.language-synoptic: o1749224057413-sub-9.7.4
- ids.tracing: hash-9ef464fc187fed823c47c3c523de876dd302271b61d42670f4d66b08e1e3cd89
- obj.clause-number: 9.7.4
- obj.element-name: unordered-list
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-2f90c5903f8d49c
- cross-reference -> prov-100000012-285e0301396b48d

#### prov-100000012-8211a559c24a49b: Modality (obj.modality) (heading)
- bib.al.original-language: en
- bib.dp.publication-date: 2025-03-01
- ids.document: 99200
- ids.element: o1749224057415-sub-9.7.5
- ids.language-synoptic: o1749224057415-sub-9.7.5
- ids.tracing: hash-4080c2e363214a6cf26c6891e0fc68bed1b309128cd3aceb0b2736729bf3a6b7
- obj.clause-number: 9.7.5
- obj.element-name: heading
- obj.language: en
- obj.specobject-type: heading
- ChapterName: 9.7.5 Modality (obj.modality)

##### tr--6d400e6f-d82a-44a1-8922-1185ec080fbf--Dk29y1A1HDCc: Modality (obj.modality) (provision)
The supplier shall provide the attribute obj.modality (8.2.1.2) for each SpecObject in the ReqIF™ file of a public standard (see 9.5).
- bib.al.original-language: en
- bib.dp.publication-date: 2025-03-01
- ids.document: 99200
- ids.element: o1749224057415-sub-9.7.5
- ids.language-synoptic: o1749224057415-sub-9.7.5
- ids.tracing: hash-cb588ce4b0ff134f326862d093a910668a126e9efbf9b542330992bb9f415d26
- obj.clause-number: 9.7.5
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-2f90c5903f8d49c
- cross-reference -> prov-100000012-f6b372b6c56a41b

#### prov-100000012-a0da07537699421: Language (obj.language) (heading)
- bib.al.original-language: en
- bib.dp.publication-date: 2025-03-01
- ids.document: 99200
- ids.element: o1749224057417-sub-9.7.6
- ids.language-synoptic: o1749224057417-sub-9.7.6
- ids.tracing: hash-5a43c898e452904f3d9383bec3a35368343057d09e51756bf57285d592382d53
- obj.clause-number: 9.7.6
- obj.element-name: heading
- obj.language: en
- obj.specobject-type: heading
- ChapterName: 9.7.6 Language (obj.language)

##### tr--6d400e6f-d82a-44a1-8922-1185ec080fbf--VYUo232T00R5: Language (obj.language) (provision)
The language for the content of the SpecObject shall be set using the corresponding value of the attribute obj.language (8.2.1.2) according to 9.1.
- bib.al.original-language: en
- bib.dp.publication-date: 2025-03-01
- ids.document: 99200
- ids.element: o1749224057417-sub-9.7.6
- ids.language-synoptic: o1749224057417-sub-9.7.6
- ids.tracing: hash-a2233443e45875d5d23e696b2da4fdd783596887c5c332ba42ff506a5ff542f4
- obj.clause-number: 9.7.6
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-2f90c5903f8d49c
- cross-reference -> prov-100000012-285e0301396b48d

##### tr--6d400e6f-d82a-44a1-8922-1185ec080fbf--sZB5j5sgpPR3: Language (obj.language) (provision)
If the source document is an XML instance and the language is not specified for the current element, language specified in the metadata of the actual document context may be assumed.
- bib.al.original-language: en
- bib.dp.publication-date: 2025-03-01
- ids.document: 99200
- ids.element: o1749224057417-sub-9.7.6
- ids.language-synoptic: o1749224057417-sub-9.7.6
- ids.tracing: hash-aa23018ae519250e27a55ff2d32e0878d95e3e4649ca7129687e1f201668476b
- obj.clause-number: 9.7.6
- obj.element-name: paragraph
- obj.language: en
- obj.modality: permission
- obj.normativity: normative
- obj.specobject-type: provision
- use.business-process: undefined
- use.business-sector: undefined
- use.interaction: undefined
- use.location: undefined
- use.product-category: undefined
- use.product-life-cycle: undefined
- use.project-phase: undefined
- use.purpose: undefined

##### tr--6d400e6f-d82a-44a1-8922-1185ec080fbf--IBOuBCGDgvNv: Language (obj.language) (provision)
The list of values for the attribute obj.language (8.2.1.2) has been reduced to focus on the common industrialized countries.
- bib.al.original-language: en
- bib.dp.publication-date: 2025-03-01
- ids.document: 99200
- ids.element: o1749224057417-sub-9.7.6
- ids.language-synoptic: o1749224057417-sub-9.7.6
- ids.tracing: hash-4d70d732c77d87b91f0498c69efbf6272f3a9df150304a74224dc7604f4e00ad
- obj.clause-number: 9.7.6
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-2f90c5903f8d49c

#### prov-100000012-b279e6c159f9422: Normativity (obj.normativity) (heading)
- bib.al.original-language: en
- bib.dp.publication-date: 2025-03-01
- ids.document: 99200
- ids.element: o1749224057419-sub-9.7.7
- ids.language-synoptic: o1749224057419-sub-9.7.7
- ids.tracing: hash-350acc194a4da80f76547b309ae82f4093a875b38c6d405c7a9176b9427dc8ce
- obj.clause-number: 9.7.7
- obj.element-name: heading
- obj.language: en
- obj.specobject-type: heading
- ChapterName: 9.7.7 Normativity (obj.normativity)

##### tr--6d400e6f-d82a-44a1-8922-1185ec080fbf--TzhDHu1tjXJx: Normativity (obj.normativity) (provision)
The supplier shall set the value of the attribute obj.normativity (8.2.1.2) for each SpecObject in the ReqIF™ file according to Annex C.
- bib.al.original-language: en
- bib.dp.publication-date: 2025-03-01
- ids.document: 99200
- ids.element: o1749224057419-sub-9.7.7
- ids.language-synoptic: o1749224057419-sub-9.7.7
- ids.tracing: hash-9e97fa61488174038bcfb9144a14a9ea54b6111407a06ec68faedbd240b22031
- obj.clause-number: 9.7.7
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-2f90c5903f8d49c
- cross-reference -> prov-100000012-823427921a7e4c8

#### prov-100000012-b62f8267193c47d: SpecObject type (obj.specobject-type) (heading)
- bib.al.original-language: en
- bib.dp.publication-date: 2025-03-01
- ids.document: 99200
- ids.element: o1749224057421-sub-9.7.8
- ids.language-synoptic: o1749224057421-sub-9.7.8
- ids.tracing: hash-2a7635e64875f3c543b7db8a93104a6e6a21433988f165a4aec35bc4a34c91db
- obj.clause-number: 9.7.8
- obj.element-name: heading
- obj.language: en
- obj.specobject-type: heading
- ChapterName: 9.7.8 SpecObject type (obj.specobject-type)

##### tr--6d400e6f-d82a-44a1-8922-1185ec080fbf--fGddF9SIjEGz: SpecObject type (obj.specobject-type) (provision)
To increase the interoperability with target systems not supporting different SpecObject types, the supplier shall set the attribute obj.specobject-type (8.2.1.2) for each SpecObject in the ReqIF™ file to:
- “document” if the SpecObject is the title page metadata or the specification of the ReqIF™ file;
- “heading” if the SpecObject is the heading of a provision:
- “provision” if the SpecObject is the content of a provision itself.
- bib.al.original-language: en
- bib.dp.publication-date: 2025-03-01
- ids.document: 99200
- ids.element: o1749224057421-sub-9.7.8
- ids.language-synoptic: o1749224057421-sub-9.7.8
- ids.tracing: hash-f0a8a61c9ffb374cb5cf7e848fa21a65c54901b613f8dc86328c6def4f2da493
- obj.clause-number: 9.7.8
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-2f90c5903f8d49c

##### prov-100000012-3d7a201c3b8e428: SpecObject type (obj.specobject-type), Note (provision)
NOTE:
Table 25 illustrates the settings of values for the listed attributes depending on the usage of either 3 different or one SpecObjectType depending on the support or lack of support in the target software.
- bib.al.original-language: en
- bib.dp.publication-date: 2025-03-01
- ids.document: 99200
- ids.element: o1749224057421-sub-9.7.8
- ids.language-synoptic: o1749224057421-sub-9.7.8
- ids.tracing: hash-21e1ca287f1b317e318a01d45ab5a5db9407326795f9a8bb996b3429512be41c
- obj.clause-number: 9.7.8
- obj.element-name: note
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
- cross-reference -> prov-100000012-4f93a8cfa6c441c

##### prov-100000012-4f93a8cfa6c441c: Setting of values depending on the SpecObjectType (provision)
Table 25 — Setting of values depending on the SpecObjectType
| attribute name | 3 SpecObjectType |  |  | 1 SpecObjectType |
| --- | --- | --- | --- | --- |
| attribute name | document | heading | provision | provision |
| ReqIF.ChapterName | no | yes | no | yes |
| ReqIF.Text | yes | no | yes | yes |
| obj.clause-heading | no | yes | yes | yes |
| obj.clause-number | no | yes | yes | yes |
| obj.specobject-type | document | heading | provision | document, heading, or provision |
- bib.al.original-language: en
- bib.dp.publication-date: 2025-03-01
- ids.document: 99200
- ids.element: o1749224057421-tab-25
- ids.language-synoptic: o1749224057421-tab-25
- ids.tracing: hash-d69cfb8e31ca12b6cc0e21146d2203cfe9dc70eadf7d86a3077ffd2e86b6bee1
- obj.clause-number: Table 25
- obj.element-name: table
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-100000012-1bcaa5aa8cac499: Conversion issues (obj.transformation-issues) (heading)
- bib.al.original-language: en
- bib.dp.publication-date: 2025-03-01
- ids.document: 99200
- ids.element: o1749224057423-sub-9.7.9
- ids.language-synoptic: o1749224057423-sub-9.7.9
- ids.tracing: hash-4c0c7854b8bb1296308fbaab6e93650c749e6dfc6c1feeb57143a204d7f2bf8b
- obj.clause-number: 9.7.9
- obj.element-name: heading
- obj.language: en
- obj.specobject-type: heading
- ChapterName: 9.7.9 Conversion issues (obj.transformation-issues)

##### tr--6d400e6f-d82a-44a1-8922-1185ec080fbf--N04myKslCGvW: Conversion issues (obj.transformation-issues) (provision)
If the source document is an XML instance, the supplier can support the users review with additional information as values of the attribute obj.transformation-issues (8.2.1.2).
- bib.al.original-language: en
- bib.dp.publication-date: 2025-03-01
- ids.document: 99200
- ids.element: o1749224057423-sub-9.7.9
- ids.language-synoptic: o1749224057423-sub-9.7.9
- ids.tracing: hash-4d2324057322de57f1eba8304ebebfc6cf140a21b3c4337375a29a3bf10d84db
- obj.clause-number: 9.7.9
- obj.element-name: paragraph
- obj.language: en
- obj.modality: permission
- obj.normativity: normative
- obj.specobject-type: provision
- obj.transformation-issues: Possibly wrong modal verb
- use.business-process: undefined
- use.business-sector: undefined
- use.interaction: undefined
- use.location: undefined
- use.product-category: undefined
- use.product-life-cycle: undefined
- use.project-phase: undefined
- use.purpose: undefined
- cross-reference -> prov-100000012-2f90c5903f8d49c

##### tr--6d400e6f-d82a-44a1-8922-1185ec080fbf--vB7XNS2icknW: Conversion issues (obj.transformation-issues) (provision)
If the attribute obj.transformation-issues (8.2.1.2) has been set for the respective SpecObject, the users can filter or sort the values to focus or prioritize the review of all SpecObjects in the ReqIF™.
- bib.al.original-language: en
- bib.dp.publication-date: 2025-03-01
- ids.document: 99200
- ids.element: o1749224057423-sub-9.7.9
- ids.language-synoptic: o1749224057423-sub-9.7.9
- ids.tracing: hash-cef6e75426677e1ab268027d8d4a0659c956245b306ea6d7ffd3cd1a89c317dd
- obj.clause-number: 9.7.9
- obj.element-name: paragraph
- obj.language: en
- obj.modality: permission
- obj.normativity: normative
- obj.specobject-type: provision
- obj.transformation-issues: Possibly wrong modal verb
- use.business-process: undefined
- use.business-sector: undefined
- use.interaction: undefined
- use.location: undefined
- use.product-category: undefined
- use.product-life-cycle: undefined
- use.project-phase: undefined
- use.purpose: undefined
- cross-reference -> prov-100000012-2f90c5903f8d49c

### prov-100000012-c256799558ec4cb: Use attributes for intra-company management (use.*) (heading)
- bib.al.original-language: en
- bib.dp.publication-date: 2025-03-01
- ids.document: 99200
- ids.element: o1749224057426-sub-9.8
- ids.language-synoptic: o1749224057426-sub-9.8
- ids.tracing: hash-4aa0a5991d09185546fdebf08c8bfe33d744857848243c9eb1e33b35ae177255
- obj.clause-number: 9.8
- obj.element-name: heading
- obj.language: en
- obj.specobject-type: heading
- ChapterName: 9.8 Use attributes for intra-company management (use.*)

#### prov-100000012-31a40d3f81b7457: Business process (use.business-process) (heading)
- bib.al.original-language: en
- bib.dp.publication-date: 2025-03-01
- ids.document: 99200
- ids.element: o1749224057428-sub-9.8.1
- ids.language-synoptic: o1749224057428-sub-9.8.1
- ids.tracing: hash-632d61f49fbb5d61a1c6c1f2d4e1b4d76f8965be909a92076e993b7fdec1d152
- obj.clause-number: 9.8.1
- obj.element-name: heading
- obj.language: en
- obj.specobject-type: heading
- ChapterName: 9.8.1 Business process (use.business-process)

##### tr--6d400e6f-d82a-44a1-8922-1185ec080fbf--1Cj9j89LHWWW: Business process (use.business-process) (provision)
The users can assign one or more values for the applicable business process where the provision is relevant.
- bib.al.original-language: en
- bib.dp.publication-date: 2025-03-01
- ids.document: 99200
- ids.element: o1749224057428-sub-9.8.1
- ids.language-synoptic: o1749224057428-sub-9.8.1
- ids.tracing: hash-c980c9d00bca342f4e58f813bbc7e5ae7eb81f14ff56422a602388dc055f9eb0
- obj.clause-number: 9.8.1
- obj.element-name: paragraph
- obj.language: en
- obj.modality: permission
- obj.normativity: normative
- obj.specobject-type: provision
- obj.transformation-issues: Possibly wrong modal verb
- use.business-process: undefined
- use.business-sector: undefined
- use.interaction: undefined
- use.location: undefined
- use.product-category: undefined
- use.product-life-cycle: undefined
- use.project-phase: undefined
- use.purpose: undefined

##### tr--6d400e6f-d82a-44a1-8922-1185ec080fbf--1WQ9MIqHEUro: Business process (use.business-process) (provision)
To achieve interoperability between different companies, the list of values for the attribute use.business-process (8.2.1.3) has been generalized to Porter [9] plus the usual supporting processes.
- bib.al.original-language: en
- bib.dp.publication-date: 2025-03-01
- ids.document: 99200
- ids.element: o1749224057428-sub-9.8.1
- ids.language-synoptic: o1749224057428-sub-9.8.1
- ids.tracing: hash-53a6b0b4b7505823b8ced5828f40cb84d0bae239d2fdfe278ef9fbe4731d92ef
- obj.clause-number: 9.8.1
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-84c18c91f471404
- cross-reference -> prov-100000012-402e6ac107ee49d

##### prov-100000012-5c00509e0bbb4b8: Business process (use.business-process) (provision)
EXAMPLE:
“production; supporting – technology development” if the requirement is relevant for the production and for the development of a product or part, e. g., a valve nozzle.
- bib.al.original-language: en
- bib.dp.publication-date: 2025-03-01
- ids.document: 99200
- ids.element: o1749224057428-sub-9.8.1
- ids.language-synoptic: o1749224057428-sub-9.8.1
- ids.tracing: hash-cc11d802ed75adfdf43183752cc3ad29f7e323b7c1d45479cbe0dd13c644cb78
- obj.clause-number: 9.8.1
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

#### prov-100000012-d71d5bca5cee40e: Business sector; industry sector (use.business-sector) (heading)
- bib.al.original-language: en
- bib.dp.publication-date: 2025-03-01
- ids.document: 99200
- ids.element: o1749224057430-sub-9.8.2
- ids.language-synoptic: o1749224057430-sub-9.8.2
- ids.tracing: hash-f5a3dd5f5c7d8928670424c10ce84157d149ce44a51170d636da306137ae4bd6
- obj.clause-number: 9.8.2
- obj.element-name: heading
- obj.language: en
- obj.specobject-type: heading
- ChapterName: 9.8.2 Business sector; industry sector (use.business-sector)

##### tr--6d400e6f-d82a-44a1-8922-1185ec080fbf--mCdKvcvN4swW: Business sector; industry sector (use.business-sector) (provision)
The users can assign one or more values for the applicable business sector where the provision is relevant.
- bib.al.original-language: en
- bib.dp.publication-date: 2025-03-01
- ids.document: 99200
- ids.element: o1749224057430-sub-9.8.2
- ids.language-synoptic: o1749224057430-sub-9.8.2
- ids.tracing: hash-9a349c2246c71121e50f8ec3bceca6d3799b6889ef4d07b98660be3ffddd8005
- obj.clause-number: 9.8.2
- obj.element-name: paragraph
- obj.language: en
- obj.modality: permission
- obj.normativity: normative
- obj.specobject-type: provision
- obj.transformation-issues: Possibly wrong modal verb
- use.business-process: undefined
- use.business-sector: undefined
- use.interaction: undefined
- use.location: undefined
- use.product-category: undefined
- use.product-life-cycle: undefined
- use.project-phase: undefined
- use.purpose: undefined

##### prov-100000012-3c893fb0b364472: Business sector; industry sector (use.business-sector) (provision)
EXAMPLE:
“industrials – mechanical engineering” if the requirement is relevant for the mechanical engineering parts of a system, e. g., a printing-on-demand line.
- bib.al.original-language: en
- bib.dp.publication-date: 2025-03-01
- ids.document: 99200
- ids.element: o1749224057430-sub-9.8.2
- ids.language-synoptic: o1749224057430-sub-9.8.2
- ids.tracing: hash-00da0626c9b9823d012b0dcc2a9ad722d12cae672ff698ac5271a95e8e0cd2c9
- obj.clause-number: 9.8.2
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

#### prov-100000012-82b93ff0a8c545b: Date usage begins (use.date-usage-begins) (heading)
- bib.al.original-language: en
- bib.dp.publication-date: 2025-03-01
- ids.document: 99200
- ids.element: o1749224057432-sub-9.8.3
- ids.language-synoptic: o1749224057432-sub-9.8.3
- ids.tracing: hash-58861af0f4362f91860f52102763b05f85b73f6a1a27f6c052d1e9aa5d34e3b4
- obj.clause-number: 9.8.3
- obj.element-name: heading
- obj.language: en
- obj.specobject-type: heading
- ChapterName: 9.8.3 Date usage begins (use.date-usage-begins)

##### tr--6d400e6f-d82a-44a1-8922-1185ec080fbf--Y2qikQLq5ks9: Date usage begins (use.date-usage-begins) (provision)
The users can assign one or more values for the applicable date when implementation of the provision is going to begin, expressed in the format YYYY-MM-DD according to DIN ISO 8601-1.
- bib.al.original-language: en
- bib.dp.publication-date: 2025-03-01
- ids.document: 99200
- ids.element: o1749224057432-sub-9.8.3
- ids.language-synoptic: o1749224057432-sub-9.8.3
- ids.tracing: hash-d9f64d787cb67d30cc838d840a61056ed8e62888a6b5c9256c265d466a52c637
- obj.clause-number: 9.8.3
- obj.element-name: paragraph
- obj.language: en
- obj.modality: permission
- obj.normativity: normative
- obj.specobject-type: provision
- obj.transformation-issues: Possibly wrong modal verb
- use.business-process: undefined
- use.business-sector: undefined
- use.interaction: undefined
- use.location: undefined
- use.product-category: undefined
- use.product-life-cycle: undefined
- use.project-phase: undefined
- use.purpose: undefined

##### prov-100000012-82f7bb1a464a415: Date usage begins (use.date-usage-begins) (provision)
EXAMPLE:
“2024-01-01” if this is date to begin the implementation of a requirement from the new medical device directive.
- bib.al.original-language: en
- bib.dp.publication-date: 2025-03-01
- ids.document: 99200
- ids.element: o1749224057432-sub-9.8.3
- ids.language-synoptic: o1749224057432-sub-9.8.3
- ids.tracing: hash-05feb253add0bba2f5288e7674bf90ff95704a6341ce99846e40bc6799891585
- obj.clause-number: 9.8.3
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

#### prov-100000012-acbd638f692f43e: Date usage ends (use.date-usage-ends) (heading)
- bib.al.original-language: en
- bib.dp.publication-date: 2025-03-01
- ids.document: 99200
- ids.element: o1749224057434-sub-9.8.4
- ids.language-synoptic: o1749224057434-sub-9.8.4
- ids.tracing: hash-a9df713bfd980416584c0733e214c2f1e2b957f1d71d0126790d0abf284d0dd1
- obj.clause-number: 9.8.4
- obj.element-name: heading
- obj.language: en
- obj.specobject-type: heading
- ChapterName: 9.8.4 Date usage ends (use.date-usage-ends)

##### tr--6d400e6f-d82a-44a1-8922-1185ec080fbf--N33oTXW33Y0Q: Date usage ends (use.date-usage-ends) (provision)
The users can assign zero or one values for the applicable date when implementation of the provision may terminate, expressed in the format YYYY-MM-DD according to DIN ISO 8601-1.
- bib.al.original-language: en
- bib.dp.publication-date: 2025-03-01
- ids.document: 99200
- ids.element: o1749224057434-sub-9.8.4
- ids.language-synoptic: o1749224057434-sub-9.8.4
- ids.tracing: hash-e3f404168cadaa1560c11acd9852266f096a5d9630325028625e88a33f57e613
- obj.clause-number: 9.8.4
- obj.element-name: paragraph
- obj.language: en
- obj.modality: permission
- obj.normativity: normative
- obj.specobject-type: provision
- obj.transformation-issues: Possibly wrong modal verb
- use.business-process: undefined
- use.business-sector: undefined
- use.interaction: undefined
- use.location: undefined
- use.product-category: undefined
- use.product-life-cycle: undefined
- use.project-phase: undefined
- use.purpose: undefined

##### prov-100000012-900c94504e3245a: Date usage ends (use.date-usage-ends) (provision)
EXAMPLE:
“2027-12-31” if this is date to end the implementation of a requirement from the new medical device directive.
- bib.al.original-language: en
- bib.dp.publication-date: 2025-03-01
- ids.document: 99200
- ids.element: o1749224057434-sub-9.8.4
- ids.language-synoptic: o1749224057434-sub-9.8.4
- ids.tracing: hash-d8d4eeb9aaafc99ed4c33e6f74f6e79318e38501d43006f2e37df48811d0f235
- obj.clause-number: 9.8.4
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

#### prov-100000012-5b4deea56420410: Interaction (use.interaction) (heading)
- bib.al.original-language: en
- bib.dp.publication-date: 2025-03-01
- ids.document: 99200
- ids.element: o1749224057436-sub-9.8.5
- ids.language-synoptic: o1749224057436-sub-9.8.5
- ids.tracing: hash-741af94a5f194261adef0638ea53b72bec869e6fa10fbf00f7e3f16750d91b4d
- obj.clause-number: 9.8.5
- obj.element-name: heading
- obj.language: en
- obj.specobject-type: heading
- ChapterName: 9.8.5 Interaction (use.interaction)

##### tr--6d400e6f-d82a-44a1-8922-1185ec080fbf--Siz4BV4dxNoo: Interaction (use.interaction) (provision)
The users can assign one or more values for a type of interaction of the provision.
- bib.al.original-language: en
- bib.dp.publication-date: 2025-03-01
- ids.document: 99200
- ids.element: o1749224057436-sub-9.8.5
- ids.language-synoptic: o1749224057436-sub-9.8.5
- ids.tracing: hash-2f95f82c417582a468bafa61f55d54a3ea909472767776f9cd109bc13c009644
- obj.clause-number: 9.8.5
- obj.element-name: paragraph
- obj.language: en
- obj.modality: permission
- obj.normativity: normative
- obj.specobject-type: provision
- obj.transformation-issues: Possibly wrong modal verb
- use.business-process: undefined
- use.business-sector: undefined
- use.interaction: undefined
- use.location: undefined
- use.product-category: undefined
- use.product-life-cycle: undefined
- use.project-phase: undefined
- use.purpose: undefined

##### prov-100000012-65d656bb55f84ef: Interaction (use.interaction) (provision)
EXAMPLE:
“integral aspect” if the requirement serves an integral aspect of a system, e. g., a railway network.
- bib.al.original-language: en
- bib.dp.publication-date: 2025-03-01
- ids.document: 99200
- ids.element: o1749224057436-sub-9.8.5
- ids.language-synoptic: o1749224057436-sub-9.8.5
- ids.tracing: hash-5078ef077b5e85e3ef70bbd1a985f92471622974b62fd7792ee9e42d41e74b20
- obj.clause-number: 9.8.5
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

#### prov-100000012-4ac5168f452b4f9: Implementation region (use.location) (heading)
- bib.al.original-language: en
- bib.dp.publication-date: 2025-03-01
- ids.document: 99200
- ids.element: o1749224057438-sub-9.8.6
- ids.language-synoptic: o1749224057438-sub-9.8.6
- ids.tracing: hash-47d4d46ec24d3548283edc68a2237a245fd7194d6fe5400ee350f89bc2e0695e
- obj.clause-number: 9.8.6
- obj.element-name: heading
- obj.language: en
- obj.specobject-type: heading
- ChapterName: 9.8.6 Implementation region (use.location)

##### tr--6d400e6f-d82a-44a1-8922-1185ec080fbf--S7coixkX3V8O: Implementation region (use.location) (provision)
The users can assign one or more values for the geological locations where the provision is going to be implemented, expressed as lower-case ALPHA-3 country code according to DIN EN ISO 3166-1.
- bib.al.original-language: en
- bib.dp.publication-date: 2025-03-01
- ids.document: 99200
- ids.element: o1749224057438-sub-9.8.6
- ids.language-synoptic: o1749224057438-sub-9.8.6
- ids.tracing: hash-5b8b077e9f07b4d738f811fdcff48cc1a7edd4da77492ae8091abdf5a2126ab1
- obj.clause-number: 9.8.6
- obj.element-name: paragraph
- obj.language: en
- obj.modality: permission
- obj.normativity: normative
- obj.specobject-type: provision
- obj.transformation-issues: Possibly wrong modal verb
- use.business-process: undefined
- use.business-sector: undefined
- use.interaction: undefined
- use.location: undefined
- use.product-category: undefined
- use.product-life-cycle: undefined
- use.project-phase: undefined
- use.purpose: undefined

##### tr--6d400e6f-d82a-44a1-8922-1185ec080fbf--XzenYRKvpwLv: Implementation region (use.location) (provision)
The list of values for the attribute use.location (8.2.1.3) has been reduced to focus on common industrialized and producing countries.
- bib.al.original-language: en
- bib.dp.publication-date: 2025-03-01
- ids.document: 99200
- ids.element: o1749224057438-sub-9.8.6
- ids.language-synoptic: o1749224057438-sub-9.8.6
- ids.tracing: hash-2295678f7cb1f7d5ca83a82057afb7cf0d6bd1ff47f83ccc7b58419bd7e21510
- obj.clause-number: 9.8.6
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-84c18c91f471404

##### tr--6d400e6f-d82a-44a1-8922-1185ec080fbf--UwgvMrh7xMtx: Implementation region (use.location) (provision)
The list of values for the attribute use.location (8.2.1.3) has been extended with additional codes to support continents and some regionally common locations.
- bib.al.original-language: en
- bib.dp.publication-date: 2025-03-01
- ids.document: 99200
- ids.element: o1749224057438-sub-9.8.6
- ids.language-synoptic: o1749224057438-sub-9.8.6
- ids.tracing: hash-ef25f0aa435ecf0f97b681107c562e799b99ba038366b1c65784e57888e73a3b
- obj.clause-number: 9.8.6
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-84c18c91f471404

##### prov-100000012-0a57682d192f44c: Implementation region (use.location) (provision)
EXAMPLE:
“eee; usa” if Europe and the United States of America are the regions where the requirement is going to be implemented, e. g., legislative regulations for the handling of person-related data within social media software.
- bib.al.original-language: en
- bib.dp.publication-date: 2025-03-01
- ids.document: 99200
- ids.element: o1749224057438-sub-9.8.6
- ids.language-synoptic: o1749224057438-sub-9.8.6
- ids.tracing: hash-05bc616bcfa01151016e8d26ddfa816367ee4d4c3d484e2b9ed556b9c7cc2448
- obj.clause-number: 9.8.6
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

#### prov-100000012-c848827cb2b04d6: Project phase (use.project-phase) (heading)
- bib.al.original-language: en
- bib.dp.publication-date: 2025-03-01
- ids.document: 99200
- ids.element: o1749224057440-sub-9.8.7
- ids.language-synoptic: o1749224057440-sub-9.8.7
- ids.tracing: hash-02b2bd21ca7de8fb1f0c33fed1a87ed4d05481d41462c0b3f5bb5a6f8cd425a0
- obj.clause-number: 9.8.7
- obj.element-name: heading
- obj.language: en
- obj.specobject-type: heading
- ChapterName: 9.8.7 Project phase (use.project-phase)

##### tr--6d400e6f-d82a-44a1-8922-1185ec080fbf--SKLeJ3dHhhqV: Project phase (use.project-phase) (provision)
The users can assign one or more values for the applicable project phase where the provision is relevant.
- bib.al.original-language: en
- bib.dp.publication-date: 2025-03-01
- ids.document: 99200
- ids.element: o1749224057440-sub-9.8.7
- ids.language-synoptic: o1749224057440-sub-9.8.7
- ids.tracing: hash-61972565deba49b26b4c042de5f83a1c675e9cac19567274d40f944bfb413da4
- obj.clause-number: 9.8.7
- obj.element-name: paragraph
- obj.language: en
- obj.modality: permission
- obj.normativity: normative
- obj.specobject-type: provision
- obj.transformation-issues: Possibly wrong modal verb
- use.business-process: undefined
- use.business-sector: undefined
- use.interaction: undefined
- use.location: undefined
- use.product-category: undefined
- use.product-life-cycle: undefined
- use.project-phase: undefined
- use.purpose: undefined

##### prov-100000012-c5cdc113df6e4b3: Project phase (use.project-phase) (provision)
EXAMPLE:
“definition and planning; execution” if the recommendation is relevant for the specification phase and the and realization phase of a project, e. g., the development of the firmware for a control unit.
- bib.al.original-language: en
- bib.dp.publication-date: 2025-03-01
- ids.document: 99200
- ids.element: o1749224057440-sub-9.8.7
- ids.language-synoptic: o1749224057440-sub-9.8.7
- ids.tracing: hash-7143a30723c243e1262276d28bc47409e7d0d09ef9c0136902c4849b42c0d955
- obj.clause-number: 9.8.7
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

#### prov-100000012-86da6802b4374c9: Product category (use.product-category) (heading)
- bib.al.original-language: en
- bib.dp.publication-date: 2025-03-01
- ids.document: 99200
- ids.element: o1749224057442-sub-9.8.8
- ids.language-synoptic: o1749224057442-sub-9.8.8
- ids.tracing: hash-6671f0acc3f42706b70d504d541595ef9faf30460544ec99e4ad668a5695e3b5
- obj.clause-number: 9.8.8
- obj.element-name: heading
- obj.language: en
- obj.specobject-type: heading
- ChapterName: 9.8.8 Product category (use.product-category)

##### tr--6d400e6f-d82a-44a1-8922-1185ec080fbf--U0zIsZ5DoINv: Product category (use.product-category) (provision)
The users can assign one or more values for the applicable product category where the provision is relevant.
- bib.al.original-language: en
- bib.dp.publication-date: 2025-03-01
- ids.document: 99200
- ids.element: o1749224057442-sub-9.8.8
- ids.language-synoptic: o1749224057442-sub-9.8.8
- ids.tracing: hash-12a56829f5ca22a7d19a4796f0e74e808712f4450d5885f4347c73e8406e2e8a
- obj.clause-number: 9.8.8
- obj.element-name: paragraph
- obj.language: en
- obj.modality: permission
- obj.normativity: normative
- obj.specobject-type: provision
- obj.transformation-issues: Possibly wrong modal verb
- use.business-process: undefined
- use.business-sector: undefined
- use.interaction: undefined
- use.location: undefined
- use.product-category: undefined
- use.product-life-cycle: undefined
- use.project-phase: undefined
- use.purpose: undefined

##### tr--6d400e6f-d82a-44a1-8922-1185ec080fbf--V2nFp1bmZGX6: Product category (use.product-category) (provision)
If the product category is used, the stakeholder relevant for the interoperability context should align on harmonized product categories.
- bib.al.original-language: en
- bib.dp.publication-date: 2025-03-01
- ids.document: 99200
- ids.element: o1749224057442-sub-9.8.8
- ids.language-synoptic: o1749224057442-sub-9.8.8
- ids.tracing: hash-674c1993d47b36700c156efee4e34dd12278a9fc39d4ffa0244350eda5d9cfb4
- obj.clause-number: 9.8.8
- obj.element-name: paragraph
- obj.language: en
- obj.modality: recommendation
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-3203da30616c4c7: Product category (use.product-category) (provision)
EXAMPLE:
“roller bearings” if the recommendation is relevant for this part of, e. g., an automobile.
- bib.al.original-language: en
- bib.dp.publication-date: 2025-03-01
- ids.document: 99200
- ids.element: o1749224057442-sub-9.8.8
- ids.language-synoptic: o1749224057442-sub-9.8.8
- ids.tracing: hash-76bf1f689ee9559aa8795fc07b8a62d91b0ac8b3fababd3efb3f92ebf749ea28
- obj.clause-number: 9.8.8
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

#### prov-100000012-52a9ac03fa9e422: Product life cycle (use.product-life-cycle) (heading)
- bib.al.original-language: en
- bib.dp.publication-date: 2025-03-01
- ids.document: 99200
- ids.element: o1749224057444-sub-9.8.9
- ids.language-synoptic: o1749224057444-sub-9.8.9
- ids.tracing: hash-11d38c0ba1b5f915804e03323a74056a509200e8e5d1439411b15877e86f655f
- obj.clause-number: 9.8.9
- obj.element-name: heading
- obj.language: en
- obj.specobject-type: heading
- ChapterName: 9.8.9 Product life cycle (use.product-life-cycle)

##### tr--6d400e6f-d82a-44a1-8922-1185ec080fbf--nFPPkEplaBJE: Product life cycle (use.product-life-cycle) (provision)
The users can assign one or more values for the applicable phase in the life cycle of a product where the provision is relevant, typically for managing the provision within a product lifecycle management (PLM) process.
- bib.al.original-language: en
- bib.dp.publication-date: 2025-03-01
- ids.document: 99200
- ids.element: o1749224057444-sub-9.8.9
- ids.language-synoptic: o1749224057444-sub-9.8.9
- ids.tracing: hash-d5ecabea38b2e15ad5a0db03497c59231fd8014fea1ea506e85e98847e23c1bb
- obj.clause-number: 9.8.9
- obj.element-name: paragraph
- obj.language: en
- obj.modality: permission
- obj.normativity: normative
- obj.specobject-type: provision
- obj.transformation-issues: Possibly wrong modal verb
- use.business-process: undefined
- use.business-sector: undefined
- use.interaction: undefined
- use.location: undefined
- use.product-category: undefined
- use.product-life-cycle: undefined
- use.project-phase: undefined
- use.purpose: undefined

##### prov-100000012-af99adb7cef8444: Product life cycle (use.product-life-cycle) (provision)
EXAMPLE:
“design; recycling” if the requirement is relevant for the design of a product or for the disposal or the recycling of a product, e. g., a lithium battery.
- bib.al.original-language: en
- bib.dp.publication-date: 2025-03-01
- ids.document: 99200
- ids.element: o1749224057444-sub-9.8.9
- ids.language-synoptic: o1749224057444-sub-9.8.9
- ids.tracing: hash-fde8eb4c80b0e8433d9591f646c51e1a85b99da1d50322d68ec33d42ca2d0ef6
- obj.clause-number: 9.8.9
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

#### prov-100000012-505cfe530103427: Purpose; intention; focus (use.purpose) (heading)
- bib.al.original-language: en
- bib.dp.publication-date: 2025-03-01
- ids.document: 99200
- ids.element: o1749224057446-sub-9.8.10
- ids.language-synoptic: o1749224057446-sub-9.8.10
- ids.tracing: hash-4dd28f6d8302a5049644960755749e7d2cc6cd0403d025630615852a80354135
- obj.clause-number: 9.8.10
- obj.element-name: heading
- obj.language: en
- obj.specobject-type: heading
- ChapterName: 9.8.10 Purpose; intention; focus (use.purpose)

##### tr--6d400e6f-d82a-44a1-8922-1185ec080fbf--Gj89MnyRZt5S: Purpose; intention; focus (use.purpose) (provision)
The users can assign one or more values for primary scope of the provision.
- bib.al.original-language: en
- bib.dp.publication-date: 2025-03-01
- ids.document: 99200
- ids.element: o1749224057446-sub-9.8.10
- ids.language-synoptic: o1749224057446-sub-9.8.10
- ids.tracing: hash-5b6954dd0bd9f23ed83198c891215f77bd6295092d744c4d9ae42aa3379970c5
- obj.clause-number: 9.8.10
- obj.element-name: paragraph
- obj.language: en
- obj.modality: permission
- obj.normativity: normative
- obj.specobject-type: provision
- obj.transformation-issues: Possibly wrong modal verb
- use.business-process: undefined
- use.business-sector: undefined
- use.interaction: undefined
- use.location: undefined
- use.product-category: undefined
- use.product-life-cycle: undefined
- use.project-phase: undefined
- use.purpose: undefined

##### prov-100000012-a03f4f034b8b430: Purpose; intention; focus (use.purpose) (provision)
EXAMPLE:
“safety” if the requirement serves to achieve safety, e. g., an emergency stop switch.
- bib.al.original-language: en
- bib.dp.publication-date: 2025-03-01
- ids.document: 99200
- ids.element: o1749224057446-sub-9.8.10
- ids.language-synoptic: o1749224057446-sub-9.8.10
- ids.tracing: hash-67e83f890f3ae8626dacb1e9f5ea3a5d54bc87ceb6f352060823ef020234e116
- obj.clause-number: 9.8.10
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### prov-100000012-e5302f19e870446: Bibliographic document metadata (bib.*) (heading)
- bib.al.original-language: en
- bib.dp.publication-date: 2025-03-01
- ids.document: 99200
- ids.element: o1749224057448-sub-9.9
- ids.language-synoptic: o1749224057448-sub-9.9
- ids.tracing: hash-d9200b002a5771236dac6575c6c7bbb36be24afea7ec3cd9008325c55787d959
- obj.clause-number: 9.9
- obj.element-name: heading
- obj.language: en
- obj.specobject-type: heading
- ChapterName: 9.9 Bibliographic document metadata (bib.*)

#### tr--6d400e6f-d82a-44a1-8922-1185ec080fbf--1eAlkNiLrUoA: Bibliographic document metadata (bib.*) (provision)
The supplier shall interpret the output for the bibliographic document metadata (see 8.2.1.4) according to the Metadata Field Specification.
- bib.al.original-language: en
- bib.dp.publication-date: 2025-03-01
- ids.document: 99200
- ids.element: o1749224057448-sub-9.9
- ids.language-synoptic: o1749224057448-sub-9.9
- ids.tracing: hash-afd35c78494fc1ae900e14dbaebe5f2f7ce2d4c9795fe2d6282fde91785336b1
- obj.clause-number: 9.9
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-ac76d054ec4c4b2

#### tr--6d400e6f-d82a-44a1-8922-1185ec080fbf--NZtTdswGgOEf: Bibliographic document metadata (bib.*) (provision)
For the International Classification System (ICS), the supplier shall set the value of the attribute bib.ca.classification (8.2.1.4) according to ISO specification, using “ICS”, the number, and the description concatenated.
- bib.al.original-language: en
- bib.dp.publication-date: 2025-03-01
- ids.document: 99200
- ids.element: o1749224057448-sub-9.9
- ids.language-synoptic: o1749224057448-sub-9.9
- ids.tracing: hash-66fcd656c2e5a6de59354690cd7735a246578f43683b472c46aa801a52860ecb
- obj.clause-number: 9.9
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-ac76d054ec4c4b2

### prov-100000012-038e236a0a004da: Identifier (ID) attributes (ids.*) (heading)
- bib.al.original-language: en
- bib.dp.publication-date: 2025-03-01
- ids.document: 99200
- ids.element: o1749224057451-sub-9.10
- ids.language-synoptic: o1749224057451-sub-9.10
- ids.tracing: hash-a6aa82f68bd8618c47b4a56c274438746b41bea315bc3bc71ee928cddf777337
- obj.clause-number: 9.10
- obj.element-name: heading
- obj.language: en
- obj.specobject-type: heading
- ChapterName: 9.10 Identifier (ID) attributes (ids.*)

#### prov-100000012-81f28831f2ef4b3: Document ID (heading)
- bib.al.original-language: en
- bib.dp.publication-date: 2025-03-01
- ids.document: 99200
- ids.element: o1749224057453-sub-9.10.1
- ids.language-synoptic: o1749224057453-sub-9.10.1
- ids.tracing: hash-87632f91996b6d3b7152438dbda2fc6fde5d3563aefb930cf3ef82edb646d7ed
- obj.clause-number: 9.10.1
- obj.element-name: heading
- obj.language: en
- obj.specobject-type: heading
- ChapterName: 9.10.1 Document ID

##### tr--6d400e6f-d82a-44a1-8922-1185ec080fbf--yuJ93gCJQboQ: Document ID (provision)
If provided, the document ID shall be unique for same version of the same document.
- bib.al.original-language: en
- bib.dp.publication-date: 2025-03-01
- ids.document: 99200
- ids.element: o1749224057453-sub-9.10.1
- ids.language-synoptic: o1749224057453-sub-9.10.1
- ids.tracing: hash-3ff5d59e06cfa03e6945e5adb272d5742926469582d64ad0601d2c618fe32932
- obj.clause-number: 9.10.1
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### tr--6d400e6f-d82a-44a1-8922-1185ec080fbf--DLl6TR33YLef: Document ID (provision)
The document ID can be used to identify documents uniquely across all documents in the target software.
- bib.al.original-language: en
- bib.dp.publication-date: 2025-03-01
- ids.document: 99200
- ids.element: o1749224057453-sub-9.10.1
- ids.language-synoptic: o1749224057453-sub-9.10.1
- ids.tracing: hash-2aa72dc968a5384d13dcf50b867a08018d1486d46a2ec7272c0eb5834149b965
- obj.clause-number: 9.10.1
- obj.element-name: paragraph
- obj.language: en
- obj.modality: permission
- obj.normativity: normative
- obj.specobject-type: provision
- obj.transformation-issues: Possibly wrong modal verb
- use.business-process: undefined
- use.business-sector: undefined
- use.interaction: undefined
- use.location: undefined
- use.product-category: undefined
- use.product-life-cycle: undefined
- use.project-phase: undefined
- use.purpose: undefined

##### tr--6d400e6f-d82a-44a1-8922-1185ec080fbf--WqVLZvjudRaS: Document ID (provision)
The supplier shall provide a document ID as value of the attribute ids.document (8.2.1.5) for each SpecObject in the ReqIF™ file.
- bib.al.original-language: en
- bib.dp.publication-date: 2025-03-01
- ids.document: 99200
- ids.element: o1749224057453-sub-9.10.1
- ids.language-synoptic: o1749224057453-sub-9.10.1
- ids.tracing: hash-486cfc652a5a1200577da6bf3e143fd66474c9f49b2ad1fdcecc217c270f28a0
- obj.clause-number: 9.10.1
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-e252dcfc668b4dc

##### tr--6d400e6f-d82a-44a1-8922-1185ec080fbf--aKiyEfLa1rPv: Document ID (provision)
The method for determining values for the document ID may follow the best-practice identified by the stakeholders relevant for the interoperability context.
- bib.al.original-language: en
- bib.dp.publication-date: 2025-03-01
- ids.document: 99200
- ids.element: o1749224057453-sub-9.10.1
- ids.language-synoptic: o1749224057453-sub-9.10.1
- ids.tracing: hash-b2dce0d986e14f0d1061aff049fc6888820f4d50d69ab1a7e1a8744329ead55d
- obj.clause-number: 9.10.1
- obj.element-name: paragraph
- obj.language: en
- obj.modality: permission
- obj.normativity: normative
- obj.specobject-type: provision
- use.business-process: undefined
- use.business-sector: undefined
- use.interaction: undefined
- use.location: undefined
- use.product-category: undefined
- use.product-life-cycle: undefined
- use.project-phase: undefined
- use.purpose: undefined

#### prov-100000012-1088c4c9414f448: Element ID (heading)
- bib.al.original-language: en
- bib.dp.publication-date: 2025-03-01
- ids.document: 99200
- ids.element: o1749224057455-sub-9.10.2
- ids.language-synoptic: o1749224057455-sub-9.10.2
- ids.tracing: hash-62340108e21f44316d096fe5f8a3f9754c6ba3e7507528466e3285d31e15e800
- obj.clause-number: 9.10.2
- obj.element-name: heading
- obj.language: en
- obj.specobject-type: heading
- ChapterName: 9.10.2 Element ID

##### tr--6d400e6f-d82a-44a1-8922-1185ec080fbf--ZtioKS2C6GS3: Element ID (provision)
If provided, the element ID shall be unique for the same fragment within the same version of the same document.
- bib.al.original-language: en
- bib.dp.publication-date: 2025-03-01
- ids.document: 99200
- ids.element: o1749224057455-sub-9.10.2
- ids.language-synoptic: o1749224057455-sub-9.10.2
- ids.tracing: hash-21fc39a5946c5696bfa1f53bbfa76e306905fa0d25dbf4e1394f31607a75b711
- obj.clause-number: 9.10.2
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### tr--6d400e6f-d82a-44a1-8922-1185ec080fbf--UpEsSWqc6ZxV: Element ID (provision)
The element ID can be used to link to fragments within target documents even if they are currently not accessible, using speaking identifiers (IDs) based on the references within the source document.
- bib.al.original-language: en
- bib.dp.publication-date: 2025-03-01
- ids.document: 99200
- ids.element: o1749224057455-sub-9.10.2
- ids.language-synoptic: o1749224057455-sub-9.10.2
- ids.tracing: hash-191b5c34e072273100dff2d3a7b571341d7df78a1316e86792f7a571c3095f5e
- obj.clause-number: 9.10.2
- obj.element-name: paragraph
- obj.language: en
- obj.modality: permission
- obj.normativity: normative
- obj.specobject-type: provision
- obj.transformation-issues: Possibly wrong modal verb
- use.business-process: undefined
- use.business-sector: undefined
- use.interaction: undefined
- use.location: undefined
- use.product-category: undefined
- use.product-life-cycle: undefined
- use.project-phase: undefined
- use.purpose: undefined

##### tr--6d400e6f-d82a-44a1-8922-1185ec080fbf--WfoAEwVJohOp: Element ID (provision)
If the source document is an XML instance, the supplier shall provide an element ID as value of the attribute ids.element (8.2.1.5) for each SpecObject in the ReqIF™ file.
- bib.al.original-language: en
- bib.dp.publication-date: 2025-03-01
- ids.document: 99200
- ids.element: o1749224057455-sub-9.10.2
- ids.language-synoptic: o1749224057455-sub-9.10.2
- ids.tracing: hash-363b96440da127f2e1386d091d1181617111a2bf3f0447f167d1feaf649db9ce
- obj.clause-number: 9.10.2
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-e252dcfc668b4dc

##### tr--6d400e6f-d82a-44a1-8922-1185ec080fbf--jubnxOGIw3Tj: Element ID (provision)
The method for determining values for the element ID may follow the best-practice identified by the stakeholders relevant for the interoperability context.
- bib.al.original-language: en
- bib.dp.publication-date: 2025-03-01
- ids.document: 99200
- ids.element: o1749224057455-sub-9.10.2
- ids.language-synoptic: o1749224057455-sub-9.10.2
- ids.tracing: hash-5c240917c11cce9f04078ef71dcac10ed444e5023699413dd79b3a0fd011112e
- obj.clause-number: 9.10.2
- obj.element-name: paragraph
- obj.language: en
- obj.modality: permission
- obj.normativity: normative
- obj.specobject-type: provision
- use.business-process: undefined
- use.business-sector: undefined
- use.interaction: undefined
- use.location: undefined
- use.product-category: undefined
- use.product-life-cycle: undefined
- use.project-phase: undefined
- use.purpose: undefined

#### prov-100000012-53b2ac39bf30450: Language-independent ID (heading)
- bib.al.original-language: en
- bib.dp.publication-date: 2025-03-01
- ids.document: 99200
- ids.element: o1749224057457-sub-9.10.3
- ids.language-synoptic: o1749224057457-sub-9.10.3
- ids.tracing: hash-2ad7b4d46acf447c850833b27ec00c33ae9bde6ac071e132e9cb70f99c28fae0
- obj.clause-number: 9.10.3
- obj.element-name: heading
- obj.language: en
- obj.specobject-type: heading
- ChapterName: 9.10.3 Language-independent ID

##### tr--6d400e6f-d82a-44a1-8922-1185ec080fbf--zXhy8E54qgne: Language-independent ID (provision)
If provided, the language-independent ID shall be unique for the same fragment across all language variants within the same version of the same document.
- bib.al.original-language: en
- bib.dp.publication-date: 2025-03-01
- ids.document: 99200
- ids.element: o1749224057457-sub-9.10.3
- ids.language-synoptic: o1749224057457-sub-9.10.3
- ids.tracing: hash-6df9c2671d04aa90138515dea7bc96a49d3d092cb180e5d0f6e0373cb71fdb74
- obj.clause-number: 9.10.3
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### tr--6d400e6f-d82a-44a1-8922-1185ec080fbf--kQVp79IjlIxW: Language-independent ID (provision)
The language-independent ID can be used to identify the synoptic fragments across all language variants within the same version of the same document.
- bib.al.original-language: en
- bib.dp.publication-date: 2025-03-01
- ids.document: 99200
- ids.element: o1749224057457-sub-9.10.3
- ids.language-synoptic: o1749224057457-sub-9.10.3
- ids.tracing: hash-0f252524adc1db7f94f8f42b865eb7d5eceeba858a4e68894577782f634da8a7
- obj.clause-number: 9.10.3
- obj.element-name: paragraph
- obj.language: en
- obj.modality: permission
- obj.normativity: normative
- obj.specobject-type: provision
- obj.transformation-issues: Possibly wrong modal verb
- use.business-process: undefined
- use.business-sector: undefined
- use.interaction: undefined
- use.location: undefined
- use.product-category: undefined
- use.product-life-cycle: undefined
- use.project-phase: undefined
- use.purpose: undefined

##### tr--6d400e6f-d82a-44a1-8922-1185ec080fbf--V6Xm1DYHzbW3: Language-independent ID (provision)
If the value of the element ID (see 9.10.2) is set to a language-dependent value, the supplier should provide the attribute ids.language-synoptic (8.2.1.5) with a language-independent value for the SpecObject.
- bib.al.original-language: en
- bib.dp.publication-date: 2025-03-01
- ids.document: 99200
- ids.element: o1749224057457-sub-9.10.3
- ids.language-synoptic: o1749224057457-sub-9.10.3
- ids.tracing: hash-94efc3c8c220587ead62c3c0805a17b24b9d6611b699a9fb8710cba770864468
- obj.clause-number: 9.10.3
- obj.element-name: paragraph
- obj.language: en
- obj.modality: recommendation
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-1088c4c9414f448
- cross-reference -> prov-100000012-e252dcfc668b4dc

##### tr--6d400e6f-d82a-44a1-8922-1185ec080fbf--pFTbrBUugGu6: Language-independent ID (provision)
The method for determining values for the language-independent ID may follow the best-practice identified by the stakeholders relevant for the interoperability context.
- bib.al.original-language: en
- bib.dp.publication-date: 2025-03-01
- ids.document: 99200
- ids.element: o1749224057457-sub-9.10.3
- ids.language-synoptic: o1749224057457-sub-9.10.3
- ids.tracing: hash-ed84d4a8dd8a81dbf56e53f67d2767168afa4370c5a83f38f624211dbcaefd22
- obj.clause-number: 9.10.3
- obj.element-name: paragraph
- obj.language: en
- obj.modality: permission
- obj.normativity: normative
- obj.specobject-type: provision
- use.business-process: undefined
- use.business-sector: undefined
- use.interaction: undefined
- use.location: undefined
- use.product-category: undefined
- use.product-life-cycle: undefined
- use.project-phase: undefined
- use.purpose: undefined

#### prov-100000012-5e2e63a2090d43b: Path-IDs (heading)
- bib.al.original-language: en
- bib.dp.publication-date: 2025-03-01
- ids.document: 99200
- ids.element: o1749224057459-sub-9.10.4
- ids.language-synoptic: o1749224057459-sub-9.10.4
- ids.tracing: hash-80a808c71be13c2e1d5c162f1d3dc555b05ca4ff00b2db7e1702047713266155
- obj.clause-number: 9.10.4
- obj.element-name: heading
- obj.language: en
- obj.specobject-type: heading
- ChapterName: 9.10.4 Path-IDs

##### tr--6d400e6f-d82a-44a1-8922-1185ec080fbf--LcG5RFhkMAhG: Path-IDs (provision)
If provided, the path IDs shall enable marking the start and the end of a fragment within the source document.
- bib.al.original-language: en
- bib.dp.publication-date: 2025-03-01
- ids.document: 99200
- ids.element: o1749224057459-sub-9.10.4
- ids.language-synoptic: o1749224057459-sub-9.10.4
- ids.tracing: hash-fa5cb40fd9dda76ee8d3a8f1ffce2c77bb81672a3f2d552f5e967e897a74082d
- obj.clause-number: 9.10.4
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### tr--6d400e6f-d82a-44a1-8922-1185ec080fbf--RoUhYqgmblYq: Path-IDs (provision)
The path IDs can be used to access fragments uniquely by using path and offset independently or below the element contexts given in the content.
- bib.al.original-language: en
- bib.dp.publication-date: 2025-03-01
- ids.document: 99200
- ids.element: o1749224057459-sub-9.10.4
- ids.language-synoptic: o1749224057459-sub-9.10.4
- ids.tracing: hash-6f9ea9421155682e2dbf978b16908b6ae7a590a243d5c8abf8f8c4b5aad951d2
- obj.clause-number: 9.10.4
- obj.element-name: paragraph
- obj.language: en
- obj.modality: permission
- obj.normativity: normative
- obj.specobject-type: provision
- obj.transformation-issues: Possibly wrong modal verb
- use.business-process: undefined
- use.business-sector: undefined
- use.interaction: undefined
- use.location: undefined
- use.product-category: undefined
- use.product-life-cycle: undefined
- use.project-phase: undefined
- use.purpose: undefined

##### tr--6d400e6f-d82a-44a1-8922-1185ec080fbf--aP5m9Yj2ozuP: Path-IDs (provision)
If the source document is an XML instance, the supplier should provide path IDs for each SpecObject in the ReqIF™ file in the form of the XPath:
- to the start of the SpecObject as value of the attribute ids.xpath-start (8.2.1.5);
- to the end of the SpecObject as value of the attribute ids.xpath-end (8.2.1.5);
- bib.al.original-language: en
- bib.dp.publication-date: 2025-03-01
- ids.document: 99200
- ids.element: o1749224057459-sub-9.10.4
- ids.language-synoptic: o1749224057459-sub-9.10.4
- ids.tracing: hash-f3b764687075be49dd6712a336d752ed754a4bc4fcbd6585d995e04cc673b501
- obj.clause-number: 9.10.4
- obj.element-name: paragraph
- obj.language: en
- obj.modality: recommendation
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-e252dcfc668b4dc

##### tr--6d400e6f-d82a-44a1-8922-1185ec080fbf--QP6fkutQBdyc: Path-IDs (provision)
If the source document is not an XML instance, the attributes shall be omitted.
- bib.al.original-language: en
- bib.dp.publication-date: 2025-03-01
- ids.document: 99200
- ids.element: o1749224057459-sub-9.10.4
- ids.language-synoptic: o1749224057459-sub-9.10.4
- ids.tracing: hash-41bcbbfdef3f59f530cb5a3393ae00be9d58ebf6852840e8e22444f613ea4b12
- obj.clause-number: 9.10.4
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### tr--6d400e6f-d82a-44a1-8922-1185ec080fbf--7sEm6UuB1qO2: Path-IDs (provision)
The method for determining values for the path IDs may follow the best-practice identified by the stakeholders relevant for the interoperability context.
- bib.al.original-language: en
- bib.dp.publication-date: 2025-03-01
- ids.document: 99200
- ids.element: o1749224057459-sub-9.10.4
- ids.language-synoptic: o1749224057459-sub-9.10.4
- ids.tracing: hash-3d56bb0e422951075dc40441d5e979854a6621c984f7396f4a43bd8f5eb85a05
- obj.clause-number: 9.10.4
- obj.element-name: paragraph
- obj.language: en
- obj.modality: permission
- obj.normativity: normative
- obj.specobject-type: provision
- use.business-process: undefined
- use.business-sector: undefined
- use.interaction: undefined
- use.location: undefined
- use.product-category: undefined
- use.product-life-cycle: undefined
- use.project-phase: undefined
- use.purpose: undefined

#### prov-100000012-754296aabcb5401: Version-independent tracing ID (heading)
- bib.al.original-language: en
- bib.dp.publication-date: 2025-03-01
- ids.document: 99200
- ids.element: o1749224057461-sub-9.10.5
- ids.language-synoptic: o1749224057461-sub-9.10.5
- ids.tracing: hash-1f0eb5e0bba76a2bc031a6c3ce3f27300da4752d598ce3fb5cdba56e2fe65fa5
- obj.clause-number: 9.10.5
- obj.element-name: heading
- obj.language: en
- obj.specobject-type: heading
- ChapterName: 9.10.5 Version-independent tracing ID

##### tr--6d400e6f-d82a-44a1-8922-1185ec080fbf--VkqxBY5VGL54: Version-independent tracing ID (provision)
If provided, the tracing ID shall be unique for the same content of the same fragment across all versions of the same document.
- bib.al.original-language: en
- bib.dp.publication-date: 2025-03-01
- ids.document: 99200
- ids.element: o1749224057461-sub-9.10.5
- ids.language-synoptic: o1749224057461-sub-9.10.5
- ids.tracing: hash-cca21efe0b67348584c104808a47a17e48a060e1e17e02898655bc45c0a83452
- obj.clause-number: 9.10.5
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### tr--6d400e6f-d82a-44a1-8922-1185ec080fbf--NXSnUcJOlIVo: Version-independent tracing ID (provision)
The tracing ID can be used to identify content of the provision that is unique within a certain clause across multiple editions of the same standard.
- bib.al.original-language: en
- bib.dp.publication-date: 2025-03-01
- ids.document: 99200
- ids.element: o1749224057461-sub-9.10.5
- ids.language-synoptic: o1749224057461-sub-9.10.5
- ids.tracing: hash-52711ef58aa63027c18faee6d91153094806019125f8d86ca3ebaadf3c96f5e1
- obj.clause-number: 9.10.5
- obj.element-name: paragraph
- obj.language: en
- obj.modality: permission
- obj.normativity: normative
- obj.specobject-type: provision
- obj.transformation-issues: Possibly wrong modal verb
- use.business-process: undefined
- use.business-sector: undefined
- use.interaction: undefined
- use.location: undefined
- use.product-category: undefined
- use.product-life-cycle: undefined
- use.project-phase: undefined
- use.purpose: undefined

##### tr--6d400e6f-d82a-44a1-8922-1185ec080fbf--iczTG8QXJOhJ: Version-independent tracing ID (provision)
The supplier should provide a tracing ID as value of the attribute ids.tracing (8.2.1.5) for each SpecObject in the ReqIF™ file.
- bib.al.original-language: en
- bib.dp.publication-date: 2025-03-01
- ids.document: 99200
- ids.element: o1749224057461-sub-9.10.5
- ids.language-synoptic: o1749224057461-sub-9.10.5
- ids.tracing: hash-00fcc62e3eeae2e027e716ba1cfcc8a9cd456d8b6e453ba2de19e61e115b385c
- obj.clause-number: 9.10.5
- obj.element-name: paragraph
- obj.language: en
- obj.modality: recommendation
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-e252dcfc668b4dc

##### tr--6d400e6f-d82a-44a1-8922-1185ec080fbf--5XsCadzo9gzM: Version-independent tracing ID (provision)
The method for determining values for the tracing ID may follow the best-practice identified by the stakeholders relevant for the interoperability context.
- bib.al.original-language: en
- bib.dp.publication-date: 2025-03-01
- ids.document: 99200
- ids.element: o1749224057461-sub-9.10.5
- ids.language-synoptic: o1749224057461-sub-9.10.5
- ids.tracing: hash-05e9b5a202ee5d3cb365224444b18d4cb025ee55ec6cdb8ee579aca1fc81ee76
- obj.clause-number: 9.10.5
- obj.element-name: paragraph
- obj.language: en
- obj.modality: permission
- obj.normativity: normative
- obj.specobject-type: provision
- use.business-process: undefined
- use.business-sector: undefined
- use.interaction: undefined
- use.location: undefined
- use.product-category: undefined
- use.product-life-cycle: undefined
- use.project-phase: undefined
- use.purpose: undefined

##### tr--6d400e6f-d82a-44a1-8922-1185ec080fbf--5A53CgRYs7Rt: Version-independent tracing ID (provision)
A tracing ID and a unique ID shall be differentiated since one and the same ID cannot be the same over all versions of the same SpecObject as well as uniquely different over all versions of all SpecObjects (see 9.10.6).
- bib.al.original-language: en
- bib.dp.publication-date: 2025-03-01
- ids.document: 99200
- ids.element: o1749224057461-sub-9.10.5
- ids.language-synoptic: o1749224057461-sub-9.10.5
- ids.tracing: hash-3449aa5d5346b092d27c0542ebd56b7d6d3b88dc7767e41b6a8f981bee59d3fd
- obj.clause-number: 9.10.5
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-6d83400052fe47a

#### prov-100000012-6d83400052fe47a: Version-dependent unique ID (heading)
- bib.al.original-language: en
- bib.dp.publication-date: 2025-03-01
- ids.document: 99200
- ids.element: o1749224057463-sub-9.10.6
- ids.language-synoptic: o1749224057463-sub-9.10.6
- ids.tracing: hash-910ae46438ad82c84526ebde8b2d33c4cec90c778dbf230994b8e8234e14ce30
- obj.clause-number: 9.10.6
- obj.element-name: heading
- obj.language: en
- obj.specobject-type: heading
- ChapterName: 9.10.6 Version-dependent unique ID

##### tr--6d400e6f-d82a-44a1-8922-1185ec080fbf--I9K7ztemgbVq: Version-dependent unique ID (provision)
If provided, the unique ID shall be globally (GUID) or universally (UUID) unique for each fragment across all documents and versions of these.
- bib.al.original-language: en
- bib.dp.publication-date: 2025-03-01
- ids.document: 99200
- ids.element: o1749224057463-sub-9.10.6
- ids.language-synoptic: o1749224057463-sub-9.10.6
- ids.tracing: hash-b593cd262a27896d43354fb07f9c1d8001fde131be2d725b039f2e8ed270a315
- obj.clause-number: 9.10.6
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### tr--6d400e6f-d82a-44a1-8922-1185ec080fbf--hx0smIhsiT9l: Version-dependent unique ID (provision)
The unique ID can be used to identify fragments uniquely across all fragments in the target software.
- bib.al.original-language: en
- bib.dp.publication-date: 2025-03-01
- ids.document: 99200
- ids.element: o1749224057463-sub-9.10.6
- ids.language-synoptic: o1749224057463-sub-9.10.6
- ids.tracing: hash-ce026146cbc311fd6fc985bb3c4dd97ede138985a789b0c6a23e6ef46156ba04
- obj.clause-number: 9.10.6
- obj.element-name: paragraph
- obj.language: en
- obj.modality: permission
- obj.normativity: normative
- obj.specobject-type: provision
- obj.transformation-issues: Possibly wrong modal verb
- use.business-process: undefined
- use.business-sector: undefined
- use.interaction: undefined
- use.location: undefined
- use.product-category: undefined
- use.product-life-cycle: undefined
- use.project-phase: undefined
- use.purpose: undefined

##### tr--6d400e6f-d82a-44a1-8922-1185ec080fbf--sFR1hruQd93K: Version-dependent unique ID (provision)
The supplier shall provide a unique ID as value of the attribute ids.unique (8.2.1.5) for each SpecObject in the ReqIF™ file.
- bib.al.original-language: en
- bib.dp.publication-date: 2025-03-01
- ids.document: 99200
- ids.element: o1749224057463-sub-9.10.6
- ids.language-synoptic: o1749224057463-sub-9.10.6
- ids.tracing: hash-d40990c22fa1190e2c1d856a87439a43d9017f7ac1b2178dedfd107aa797d154
- obj.clause-number: 9.10.6
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-e252dcfc668b4dc

##### tr--6d400e6f-d82a-44a1-8922-1185ec080fbf--wmd12OSnvMba: Version-dependent unique ID (provision)
The method for determining values for the unique ID may follow the best-practice identified by the stakeholders relevant for the interoperability context.
- bib.al.original-language: en
- bib.dp.publication-date: 2025-03-01
- ids.document: 99200
- ids.element: o1749224057463-sub-9.10.6
- ids.language-synoptic: o1749224057463-sub-9.10.6
- ids.tracing: hash-c9aee2b945cb4206d2376a626265f0290ecd372c6804626f8abc127f41b325f6
- obj.clause-number: 9.10.6
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### tr--6d400e6f-d82a-44a1-8922-1185ec080fbf--c3e7F8DRJdvF: Version-dependent unique ID (provision)
A tracing ID and a unique ID shall be differentiated since one and the same ID cannot be the same over all versions of the same SpecObject (see 9.10.5) as well as uniquely different over all versions of all SpecObjects.
- bib.al.original-language: en
- bib.dp.publication-date: 2025-03-01
- ids.document: 99200
- ids.element: o1749224057463-sub-9.10.6
- ids.language-synoptic: o1749224057463-sub-9.10.6
- ids.tracing: hash-3a056136dad5ec38743089f6043a1659302a97f8ba0f9cd0dd662a4dc876aa72
- obj.clause-number: 9.10.6
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-754296aabcb5401

##### prov-100000012-6583f41143a344e: Version-dependent unique ID, Note (provision)
NOTE:
If UUID v5 [10] is used as method for determine values for the unique ID, different stakeholders can achieve generating the same unique value for the same namespace and the same input string.
- bib.al.original-language: en
- bib.dp.publication-date: 2025-03-01
- ids.document: 99200
- ids.element: o1749224057463-sub-9.10.6
- ids.language-synoptic: o1749224057463-sub-9.10.6
- ids.tracing: hash-15c6cb61eea24ff8cf9c0b68556210092d9a0bc8daf642d3811878f6c988a611
- obj.clause-number: 9.10.6
- obj.element-name: note
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
- cross-reference -> prov-100000012-402e6ac107ee49d

### prov-100000012-18db2eab6e9f460: Document asset or service metadata of the creator, supplier, or publisher (pub.*) (heading)
- bib.al.original-language: en
- bib.dp.publication-date: 2025-03-01
- ids.document: 99200
- ids.element: o1749224057466-sub-9.11
- ids.language-synoptic: o1749224057466-sub-9.11
- ids.tracing: hash-f5f212681b79fe8d9d43e754e64bc45f6240b498c5ac2b4f4c6f6b01b60d38c0
- obj.clause-number: 9.11
- obj.element-name: heading
- obj.language: en
- obj.specobject-type: heading
- ChapterName: 9.11 Document asset or service metadata of the creator, supplier, or publisher (pub.*)

#### prov-100000012-b458a4147df84c2: Originator (pub.originator) (heading)
- bib.al.original-language: en
- bib.dp.publication-date: 2025-03-01
- ids.document: 99200
- ids.element: o1749224057468-sub-9.11.1
- ids.language-synoptic: o1749224057468-sub-9.11.1
- ids.tracing: hash-0202e979de2fb837d97f461795cc14e64bcbd1f21aa675aa3f4cc62650803c03
- obj.clause-number: 9.11.1
- obj.element-name: heading
- obj.language: en
- obj.specobject-type: heading
- ChapterName: 9.11.1 Originator (pub.originator)

##### tr--6d400e6f-d82a-44a1-8922-1185ec080fbf--v5mCjEaQGpEw: Originator (pub.originator) (provision)
The supplier shall provide the abbreviation or short name of the originator as value of the attribute pub.originator (8.2.2) for each ReqIF™ file of a public standard (see 9.5).
- bib.al.original-language: en
- bib.dp.publication-date: 2025-03-01
- ids.document: 99200
- ids.element: o1749224057468-sub-9.11.1
- ids.language-synoptic: o1749224057468-sub-9.11.1
- ids.tracing: hash-1cd758281392f49b083d30ebbd9ac0a1618623561ceadc2cb078cb9666354d6c
- obj.clause-number: 9.11.1
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-3f46a8f6af35401
- cross-reference -> prov-100000012-f6b372b6c56a41b

##### prov-100000012-774f576cdee74ef: Originator (pub.originator) (provision)
EXAMPLE:
“DIN*DKE*CEN*CENELEC*IEC*ISO”
- bib.al.original-language: en
- bib.dp.publication-date: 2025-03-01
- ids.document: 99200
- ids.element: o1749224057468-sub-9.11.1
- ids.language-synoptic: o1749224057468-sub-9.11.1
- ids.tracing: hash-246298e6bf4eb5dd5b2c795f660acfb4ecf119de19d7890babc982fb39904667
- obj.clause-number: 9.11.1
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

#### prov-100000012-1aab42c1ee85458: Harmonization (pub.harmonization) (heading)
- bib.al.original-language: en
- bib.dp.publication-date: 2025-03-01
- ids.document: 99200
- ids.element: o1749224057470-sub-9.11.2
- ids.language-synoptic: o1749224057470-sub-9.11.2
- ids.tracing: hash-7e574a72894f84e00272549f937d33b1071b87d555a80fd8c1732c607d9b024b
- obj.clause-number: 9.11.2
- obj.element-name: heading
- obj.language: en
- obj.specobject-type: heading
- ChapterName: 9.11.2 Harmonization (pub.harmonization)

##### tr--6d400e6f-d82a-44a1-8922-1185ec080fbf--bAkkT0DTMnBZ: Harmonization (pub.harmonization) (provision)
The supplier shall provide the harmonization string for the level of harmonization and version number as value of the attribute pub.harmonization (8.2.2) for each ReqIF™ file of a public standard (see 9.5).
- bib.al.original-language: en
- bib.dp.publication-date: 2025-03-01
- ids.document: 99200
- ids.element: o1749224057470-sub-9.11.2
- ids.language-synoptic: o1749224057470-sub-9.11.2
- ids.tracing: hash-d90a29da3b6450d2e5d4720089b710ff9375138576c18ee8474b01b23977ad5f
- obj.clause-number: 9.11.2
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-3f46a8f6af35401
- cross-reference -> prov-100000012-f6b372b6c56a41b

##### prov-100000012-7468071e3a9d416: Harmonization (pub.harmonization) (provision)
EXAMPLE:
“IDiS ReqIF™ interpretation for public standards 1.3”
- bib.al.original-language: en
- bib.dp.publication-date: 2025-03-01
- ids.document: 99200
- ids.element: o1749224057470-sub-9.11.2
- ids.language-synoptic: o1749224057470-sub-9.11.2
- ids.tracing: hash-97865407c2463b1de59cb7e966301144253cead104a27345e02216efd33f01ea
- obj.clause-number: 9.11.2
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

#### prov-100000012-b101fc3b61ca445: Software (pub.software) (heading)
- bib.al.original-language: en
- bib.dp.publication-date: 2025-03-01
- ids.document: 99200
- ids.element: o1749224057472-sub-9.11.3
- ids.language-synoptic: o1749224057472-sub-9.11.3
- ids.tracing: hash-ec50b47b9940c9d78b344c2c0de9ab00096bb4fdb3ffb33394fdf1d776ce253b
- obj.clause-number: 9.11.3
- obj.element-name: heading
- obj.language: en
- obj.specobject-type: heading
- ChapterName: 9.11.3 Software (pub.software)

##### tr--6d400e6f-d82a-44a1-8922-1185ec080fbf--DLhGAAjB2fVa: Software (pub.software) (provision)
The supplier shall provide the identification string for software + version as value of the attribute pub.software (8.2.2) for each ReqIF™ file of a public standard (see 9.5).
- bib.al.original-language: en
- bib.dp.publication-date: 2025-03-01
- ids.document: 99200
- ids.element: o1749224057472-sub-9.11.3
- ids.language-synoptic: o1749224057472-sub-9.11.3
- ids.tracing: hash-c69decdd47caba7ca100de2bfb5a7078e50cd7564262ba5332d6a56027396059
- obj.clause-number: 9.11.3
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-3f46a8f6af35401
- cross-reference -> prov-100000012-f6b372b6c56a41b

##### prov-100000012-0d83e05f30eb4f0: Software (pub.software) (provision)
EXAMPLE:
“X-Swift sts2reqif-42.17.4”
- bib.al.original-language: en
- bib.dp.publication-date: 2025-03-01
- ids.document: 99200
- ids.element: o1749224057472-sub-9.11.3
- ids.language-synoptic: o1749224057472-sub-9.11.3
- ids.tracing: hash-aab565240f0669c610cf585fda157ad1e1f432cb1fe8dc5a89d9eb752cbfe494
- obj.clause-number: 9.11.3
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

#### prov-100000012-4ef40bdb0069471: Supplier (pub.supplier) (heading)
- bib.al.original-language: en
- bib.dp.publication-date: 2025-03-01
- ids.document: 99200
- ids.element: o1749224057474-sub-9.11.4
- ids.language-synoptic: o1749224057474-sub-9.11.4
- ids.tracing: hash-ee1ffefd8d819df61d51df493f5275c5cb0666a8935410cefa32caa4de7c8f89
- obj.clause-number: 9.11.4
- obj.element-name: heading
- obj.language: en
- obj.specobject-type: heading
- ChapterName: 9.11.4 Supplier (pub.supplier)

##### tr--6d400e6f-d82a-44a1-8922-1185ec080fbf--RwTtMmWstYOp: Supplier (pub.supplier) (provision)
The supplier shall provide the abbreviation or short name of the supplier as value of the attribute pub.supplier (8.2.2) for each ReqIF™ file of a public standard (see 9.5).
- bib.al.original-language: en
- bib.dp.publication-date: 2025-03-01
- ids.document: 99200
- ids.element: o1749224057474-sub-9.11.4
- ids.language-synoptic: o1749224057474-sub-9.11.4
- ids.tracing: hash-3ac097a17fd21631c3b3371650e627caba70175431ac65875817db30bde63244
- obj.clause-number: 9.11.4
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-3f46a8f6af35401
- cross-reference -> prov-100000012-f6b372b6c56a41b

##### prov-100000012-07fca48f64b741e: Supplier (pub.supplier) (provision)
EXAMPLE:
- “DIN Media”
- “VDE VERLAG”
- bib.al.original-language: en
- bib.dp.publication-date: 2025-03-01
- ids.document: 99200
- ids.element: o1749224057474-sub-9.11.4
- ids.language-synoptic: o1749224057474-sub-9.11.4
- ids.tracing: hash-97430ed2578b0e1282c568a6594ffb95ff838b28b0e62b2194050cb28b132d77
- obj.clause-number: 9.11.4
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

## prov-100000012-5934fd9e743b4e2: Presentation (heading)
- bib.al.original-language: en
- bib.dp.publication-date: 2025-03-01
- ids.document: 99200
- ids.element: o1749224057477-sub-10
- ids.language-synoptic: o1749224057477-sub-10
- ids.tracing: hash-5b56d73dd845d3faa6c6f63732dadbd3ffd38e60166212392d055f1fce431d8c
- obj.clause-number: 10
- obj.element-name: heading
- obj.language: en
- obj.specobject-type: heading
- ChapterName: 10 Presentation

### prov-100000012-1a77885f9aa34d0: Change marks in the text (heading)
- bib.al.original-language: en
- bib.dp.publication-date: 2025-03-01
- ids.document: 99200
- ids.element: o1749224057479-sub-10.1
- ids.language-synoptic: o1749224057479-sub-10.1
- ids.tracing: hash-fdb2ef36c179e674b5fa984d6ec85df8eb7cdfb714b70e3e8e1f1311fd363983
- obj.clause-number: 10.1
- obj.element-name: heading
- obj.language: en
- obj.specobject-type: heading
- ChapterName: 10.1 Change marks in the text

#### tr--6d400e6f-d82a-44a1-8922-1185ec080fbf--oQ8RfDY1Pdqr: Change marks in the text (provision)
As change marks in the text of the source document should be supported with a different presentation:
- deletion;
- insertion;
- change (other than explicitly specified deletions or insertions).
- bib.al.original-language: en
- bib.dp.publication-date: 2025-03-01
- ids.document: 99200
- ids.element: o1749224057479-sub-10.1
- ids.language-synoptic: o1749224057479-sub-10.1
- ids.tracing: hash-9a49f1624e56d84ed74d19a1eda520e6a248df763377be6d7037daeb001b29b9
- obj.clause-number: 10.1
- obj.element-name: paragraph
- obj.language: en
- obj.modality: recommendation
- obj.normativity: normative
- obj.specobject-type: provision
- use.business-process: undefined
- use.business-sector: undefined
- use.interaction: undefined
- use.location: undefined
- use.product-category: undefined
- use.product-life-cycle: undefined
- use.project-phase: undefined
- use.purpose: undefined

### prov-100000012-9af61d186e40429: Labelling and numbering (heading)
- bib.al.original-language: en
- bib.dp.publication-date: 2025-03-01
- ids.document: 99200
- ids.element: o1749224057482-sub-10.2
- ids.language-synoptic: o1749224057482-sub-10.2
- ids.tracing: hash-5abe15c4088c2a9cd5fa2bfe49f76d34fde2d44d75980db3f33e7cb5ba87b5f4
- obj.clause-number: 10.2
- obj.element-name: heading
- obj.language: en
- obj.specobject-type: heading
- ChapterName: 10.2 Labelling and numbering

#### prov-100000012-9c8e829c89ba41d: Output position of the label (heading)
- bib.al.original-language: en
- bib.dp.publication-date: 2025-03-01
- ids.document: 99200
- ids.element: o1749224057484-sub-10.2.1
- ids.language-synoptic: o1749224057484-sub-10.2.1
- ids.tracing: hash-a21f2b7f81b6ae46f43d6367876ef78135e304493e596ab783d6a11eefd8c677
- obj.clause-number: 10.2.1
- obj.element-name: heading
- obj.language: en
- obj.specobject-type: heading
- ChapterName: 10.2.1 Output position of the label

##### tr--6d400e6f-d82a-44a1-8922-1185ec080fbf--ZmCCee7LWIFG: Output position of the label (provision)
The original labelling and numbering of the public standard shall be output as:
- prefix in the content of the SpecObject, i. e. value of either the attribute ReqIF.ChapterName (9.6.1) or the attribute ReqIF.Text (9.6.2); and
- value of the attribute obj.clause-number (9.7.2).
- bib.al.original-language: en
- bib.dp.publication-date: 2025-03-01
- ids.document: 99200
- ids.element: o1749224057484-sub-10.2.1
- ids.language-synoptic: o1749224057484-sub-10.2.1
- ids.tracing: hash-b4a1a3646abd158a43264e3a6f26024e11b2ff3e17dfd94675195fb01510f208
- obj.clause-number: 10.2.1
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-18bc1f195ab945a
- cross-reference -> prov-100000012-ed8a82f3f64d4bb
- cross-reference -> prov-100000012-88079988895141e

#### prov-100000012-9d0e6334c323435: Presentation aspects for labels (heading)
- bib.al.original-language: en
- bib.dp.publication-date: 2025-03-01
- ids.document: 99200
- ids.element: o1749224057486-sub-10.2.2
- ids.language-synoptic: o1749224057486-sub-10.2.2
- ids.tracing: hash-08d0371ab3b8ae8e7da9871ca2e8356e42239b4546ba49016520dbc334b44cc4
- obj.clause-number: 10.2.2
- obj.element-name: heading
- obj.language: en
- obj.specobject-type: heading
- ChapterName: 10.2.2 Presentation aspects for labels

##### tr--6d400e6f-d82a-44a1-8922-1185ec080fbf--w6OVOMsJdlDN: Presentation aspects for labels (provision)
Labels and numbering from the document (label) shall be output both as an attribute value and in the content with separators (see Example 1).
- bib.al.original-language: en
- bib.dp.publication-date: 2025-03-01
- ids.document: 99200
- ids.element: o1749224057486-sub-10.2.2
- ids.language-synoptic: o1749224057486-sub-10.2.2
- ids.tracing: hash-2902e8013e6402cc47a1e27c7c5740ea7e788a8c096a41a9133d9d33d1f27347
- obj.clause-number: 10.2.2
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-22cc702e24ce4f7

##### prov-100000012-22cc702e24ce4f7: Presentation aspects for labels (provision)
EXAMPLE 1:
List items with enumeration letters and period separator included in the output:
<THE-VALUE> <xhtml:div> <xhtml:p xml:lang="en">The organization shall retain documented ...:</xhtml:p> <xhtml:ul> <xhtml:li><xhtml:span>a. </xhtml:span>on the results of the review;</xhtml:li> <xhtml:li><xhtml:span>b. </xhtml:span>on any new requirements ...</xhtml:li> </xhtml:ul> </xhtml:div> <THE-VALUE>
- bib.al.original-language: en
- bib.dp.publication-date: 2025-03-01
- ids.document: 99200
- ids.element: o1749224057486-sub-10.2.2
- ids.language-synoptic: o1749224057486-sub-10.2.2
- ids.tracing: hash-ffc76b24b7ccf77b5b25d8ca1902497a623aae2becb87ed210e4ef738e488ff5
- obj.clause-number: 10.2.2
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

##### tr--6d400e6f-d82a-44a1-8922-1185ec080fbf--CJGCTw2cUZaZ: Presentation aspects for labels (provision)
The format characters before and after the label may be standardized instead of following individual variants of the publishers, as long as this does not affect the interpretation of the provisions (see Example 2).
- bib.al.original-language: en
- bib.dp.publication-date: 2025-03-01
- ids.document: 99200
- ids.element: o1749224057486-sub-10.2.2
- ids.language-synoptic: o1749224057486-sub-10.2.2
- ids.tracing: hash-deb1bb4e92c1a15b1aad552767d829f7a0b8f991ef2d9945cb8369a43640dcf4
- obj.clause-number: 10.2.2
- obj.element-name: paragraph
- obj.language: en
- obj.modality: permission
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-3698f95ce6d64fc

##### prov-100000012-3698f95ce6d64fc: Presentation aspects for labels (provision)
EXAMPLE 2:
List items with standard parentheses instead of non-standard variant period as separator:
<THE-VALUE> <xhtml:div> <xhtml:p xml:lang="en">The organization shall retain documented ...:</xhtml:p> <xhtml:ul> <xhtml:li><xhtml:span>a) </xhtml:span>on the results of the review;</xhtml:li> <xhtml:li><xhtml:span>b) </xhtml:span>on any new requirements ...</xhtml:li> </xhtml:ul> </xhtml:div> <THE-VALUE>
- bib.al.original-language: en
- bib.dp.publication-date: 2025-03-01
- ids.document: 99200
- ids.element: o1749224057486-sub-10.2.2
- ids.language-synoptic: o1749224057486-sub-10.2.2
- ids.tracing: hash-9ff195cf6fa405865d34877c270eaf820815a5f275663f388b3dfcc77b1a427b
- obj.clause-number: 10.2.2
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

##### tr--6d400e6f-d82a-44a1-8922-1185ec080fbf--cpFTxazLNFpp: Presentation aspects for labels (provision)
The entry number for terms shall be output in the SpecObject as a heading, separate from the preferred term, to comply with the structure of terminological entries according to DIN ISO 10241-1 (see Example 3).
- bib.al.original-language: en
- bib.dp.publication-date: 2025-03-01
- ids.document: 99200
- ids.element: o1749224057486-sub-10.2.2
- ids.language-synoptic: o1749224057486-sub-10.2.2
- ids.tracing: hash-cc158abcda700e33341cf795e5cf407a76d7a2eb44bf15165112f35b3bc2de79
- obj.clause-number: 10.2.2
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-0ffaeea3ed3a407

##### prov-100000012-0ffaeea3ed3a407: Presentation aspects for labels (provision)
EXAMPLE 3:
Terminological entry with term number 3.1, the preferred term and the definition.
<THE-VALUE> <xhtml:div> <xhtml:p id="term_3.1" xml:lang="en"><xhtml:b>3.1</xhtml:b></xhtml:p> <xhtml:div xml:lang="en"> <xhtml:div><xhtml:b>local thickness</xhtml:b></xhtml:div> <xhtml:div>the mean of the thickness measurements, of which a ...</xhtml:div> </xhtml:div> </xhtml:div> </THE-VALUE>
- bib.al.original-language: en
- bib.dp.publication-date: 2025-03-01
- ids.document: 99200
- ids.element: o1749224057486-sub-10.2.2
- ids.language-synoptic: o1749224057486-sub-10.2.2
- ids.tracing: hash-ebf54dd072902a383506493a0b4295738191cf628d38e67a3360e21fe24e4360
- obj.clause-number: 10.2.2
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### prov-100000012-360a814824a84ec: Figures and other types of graphics (heading)
- bib.al.original-language: en
- bib.dp.publication-date: 2025-03-01
- ids.document: 99200
- ids.element: o1749224057489-sub-10.3
- ids.language-synoptic: o1749224057489-sub-10.3
- ids.tracing: hash-8296f7210ee6fe3acee9679a6737ac7bc30f7dd6ca038fc86db1bb4c436b12b1
- obj.clause-number: 10.3
- obj.element-name: heading
- obj.language: en
- obj.specobject-type: heading
- ChapterName: 10.3 Figures and other types of graphics

#### prov-100000012-93aea9deeae94ab: Types of graphics (heading)
- bib.al.original-language: en
- bib.dp.publication-date: 2025-03-01
- ids.document: 99200
- ids.element: o1749224057491-sub-10.3.1
- ids.language-synoptic: o1749224057491-sub-10.3.1
- ids.tracing: hash-ecd4e529b6d41d7778370d45df5be61bac0079419552ba0a6f15bdb37dce2efe
- obj.clause-number: 10.3.1
- obj.element-name: heading
- obj.language: en
- obj.specobject-type: heading
- ChapterName: 10.3.1 Types of graphics

##### tr--6d400e6f-d82a-44a1-8922-1185ec080fbf--LOWBFfU7GosR: Types of graphics (provision)
Provisions for raster images shall be applied for all types of graphics in the ReqIF™ for the public standard (see 10.3.2, 10.3.3, 10.3.4).
- bib.al.original-language: en
- bib.dp.publication-date: 2025-03-01
- ids.document: 99200
- ids.element: o1749224057491-sub-10.3.1
- ids.language-synoptic: o1749224057491-sub-10.3.1
- ids.tracing: hash-53cb3d2e13bd89cadc4fd07ec723d017526d5a0e282aa7e558437483fb95643d
- obj.clause-number: 10.3.1
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-4a8fdfe9a153455
- cross-reference -> prov-100000012-42850cffa9e6447
- cross-reference -> prov-100000012-0b94f90e970340b

##### prov-100000012-65486e6faa4e4f3: Types of graphics (provision)
EXAMPLE:
- figures with labelled captions,
- any graphics in tables or in the text,
- formulas rendered as graphics,
- tables rendered as graphics.
- bib.al.original-language: en
- bib.dp.publication-date: 2025-03-01
- ids.document: 99200
- ids.element: o1749224057491-sub-10.3.1
- ids.language-synoptic: o1749224057491-sub-10.3.1
- ids.tracing: hash-f65296beda8544894b1763bd1e9bcfd26de8c5ca66e645c78e4e4d21e30c8b37
- obj.clause-number: 10.3.1
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

#### prov-100000012-4a8fdfe9a153455: Graphics format (heading)
- bib.al.original-language: en
- bib.dp.publication-date: 2025-03-01
- ids.document: 99200
- ids.element: o1749224057493-sub-10.3.2
- ids.language-synoptic: o1749224057493-sub-10.3.2
- ids.tracing: hash-b6fae4b4af287a2a6e48c10c596993c2aec51939fb16081813327e73f924a395
- obj.clause-number: 10.3.2
- obj.element-name: heading
- obj.language: en
- obj.specobject-type: heading
- ChapterName: 10.3.2 Graphics format

##### tr--6d400e6f-d82a-44a1-8922-1185ec080fbf--WgDEqCe98UTl: Graphics format (provision)
The supplier shall provide all graphics as Portable Network Graphics (PNG).
- bib.al.original-language: en
- bib.dp.publication-date: 2025-03-01
- ids.document: 99200
- ids.element: o1749224057493-sub-10.3.2
- ids.language-synoptic: o1749224057493-sub-10.3.2
- ids.tracing: hash-91b33d7a505b3674f79a6a39ffa7eea1a09401b509f6e1f1eb4ed3d91b401bc7
- obj.clause-number: 10.3.2
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

#### prov-100000012-42850cffa9e6447: Graphics compression (heading)
- bib.al.original-language: en
- bib.dp.publication-date: 2025-03-01
- ids.document: 99200
- ids.element: o1749224057495-sub-10.3.3
- ids.language-synoptic: o1749224057495-sub-10.3.3
- ids.tracing: hash-304a2a51b1d65dec3e0ee7738ee7457e5cfbfd5e9c3125521ef79da11683b4d4
- obj.clause-number: 10.3.3
- obj.element-name: heading
- obj.language: en
- obj.specobject-type: heading
- ChapterName: 10.3.3 Graphics compression

##### tr--6d400e6f-d82a-44a1-8922-1185ec080fbf--SjFDquugfqS7: Graphics compression (provision)
The supplier should provide all graphics using the lossless compression optimized for minimal file size to ensure fast processing and to save storage space.
- bib.al.original-language: en
- bib.dp.publication-date: 2025-03-01
- ids.document: 99200
- ids.element: o1749224057495-sub-10.3.3
- ids.language-synoptic: o1749224057495-sub-10.3.3
- ids.tracing: hash-006e506bf2885a23a32512fad3a061229ff769d10ebb46b091e70ff6ceb8dfea
- obj.clause-number: 10.3.3
- obj.element-name: paragraph
- obj.language: en
- obj.modality: recommendation
- obj.normativity: normative
- obj.specobject-type: provision
- use.business-process: undefined
- use.business-sector: undefined
- use.interaction: undefined
- use.location: undefined
- use.product-category: undefined
- use.product-life-cycle: undefined
- use.project-phase: undefined
- use.purpose: undefined

#### prov-100000012-0b94f90e970340b: Graphics resolution (heading)
- bib.al.original-language: en
- bib.dp.publication-date: 2025-03-01
- ids.document: 99200
- ids.element: o1749224057497-sub-10.3.4
- ids.language-synoptic: o1749224057497-sub-10.3.4
- ids.tracing: hash-e504413c7a65c9b49a008293b5ce23ba8ae8e87f5ee24de28d36a56a98498e29
- obj.clause-number: 10.3.4
- obj.element-name: heading
- obj.language: en
- obj.specobject-type: heading
- ChapterName: 10.3.4 Graphics resolution

##### tr--6d400e6f-d82a-44a1-8922-1185ec080fbf--yg1zqBsGRPcl: Graphics resolution (provision)
The supplier shall provide all graphics in a resolution that can be rendered without issues relevant for the interpretation of provisions.
- bib.al.original-language: en
- bib.dp.publication-date: 2025-03-01
- ids.document: 99200
- ids.element: o1749224057497-sub-10.3.4
- ids.language-synoptic: o1749224057497-sub-10.3.4
- ids.tracing: hash-37d65f27a6bef2f390e06af71b8deaa2db8dfe63197a14fae1112d997f485c72
- obj.clause-number: 10.3.4
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-637eaf65cf0d433: Graphics resolution, Note (provision)
NOTE:
Following conventions for ISO, IEC, CEN, CENELEC, DIN and DKE deliverables, recommended resolutions are:
- If online variants with anti-aliasing are included, the resolution should be 90 dpi or higher.
- If print variants are included, the resolution should be 600 dpi.
- bib.al.original-language: en
- bib.dp.publication-date: 2025-03-01
- ids.document: 99200
- ids.element: o1749224057497-sub-10.3.4
- ids.language-synoptic: o1749224057497-sub-10.3.4
- ids.tracing: hash-340197b3ef5e127d2f8ec2cfba2f8749dadb47a5f149c8b0beb505eae8ac9aaa
- obj.clause-number: 10.3.4
- obj.element-name: note
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### prov-100000012-97010be88604461: Formulas (heading)
- bib.al.original-language: en
- bib.dp.publication-date: 2025-03-01
- ids.document: 99200
- ids.element: o1749224057500-sub-10.4
- ids.language-synoptic: o1749224057500-sub-10.4
- ids.tracing: hash-0040bb32095add3bdfa7d2fe57a04a74cbde0b8428e7f9e76042fef28055b9b8
- obj.clause-number: 10.4
- obj.element-name: heading
- obj.language: en
- obj.specobject-type: heading
- ChapterName: 10.4 Formulas

#### prov-100000012-c6c195799f914e4: Formula format (heading)
- bib.al.original-language: en
- bib.dp.publication-date: 2025-03-01
- ids.document: 99200
- ids.element: o1749224057502-sub-10.4.1
- ids.language-synoptic: o1749224057502-sub-10.4.1
- ids.tracing: hash-0b549c3cd8c9ff8cc5ca7e29238539552e89f9a5fe36e981d39a80044825445e
- obj.clause-number: 10.4.1
- obj.element-name: heading
- obj.language: en
- obj.specobject-type: heading
- ChapterName: 10.4.1 Formula format

##### tr--6d400e6f-d82a-44a1-8922-1185ec080fbf--4sLdC2D0f795: Formula format (provision)
For character-encoded output, MathML 3.0 presentational markup shall be used according to ISO/IEC 40314.
- bib.al.original-language: en
- bib.dp.publication-date: 2025-03-01
- ids.document: 99200
- ids.element: o1749224057502-sub-10.4.1
- ids.language-synoptic: o1749224057502-sub-10.4.1
- ids.tracing: hash-a1e02a560d06300073f05b7962820a08f663821b24ce1ee513280fd9334aabe0
- obj.clause-number: 10.4.1
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### tr--6d400e6f-d82a-44a1-8922-1185ec080fbf--3TTywwszzxKX: Formula format (provision)
To ensure rendering in common web browsers, all MathML markup shall be output according to the W3C MathML Core subset.
- bib.al.original-language: en
- bib.dp.publication-date: 2025-03-01
- ids.document: 99200
- ids.element: o1749224057502-sub-10.4.1
- ids.language-synoptic: o1749224057502-sub-10.4.1
- ids.tracing: hash-a54586c9741d37e65ca5618fbf4ee8abf4d7c5a2790773adfa356eedb66655f6
- obj.clause-number: 10.4.1
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-a9be25e0e0aa400: Formula format, Note (provision)
NOTE:
For more information about MathML in web browsers see [11].
- bib.al.original-language: en
- bib.dp.publication-date: 2025-03-01
- ids.document: 99200
- ids.element: o1749224057502-sub-10.4.1
- ids.language-synoptic: o1749224057502-sub-10.4.1
- ids.tracing: hash-0f26ae579ff5973310f2fcb80b1b35776c9ce8216226604b7add59d7b97bf6c7
- obj.clause-number: 10.4.1
- obj.element-name: note
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
- cross-reference -> prov-100000012-402e6ac107ee49d

#### prov-100000012-6a43f4b8937c486: Formula output (heading)
- bib.al.original-language: en
- bib.dp.publication-date: 2025-03-01
- ids.document: 99200
- ids.element: o1749224057504-sub-10.4.2
- ids.language-synoptic: o1749224057504-sub-10.4.2
- ids.tracing: hash-dd16e16d246b8a6b2222d2e9cd7810ebb91e2591d132e06512cdcaacb9e77a60
- obj.clause-number: 10.4.2
- obj.element-name: heading
- obj.language: en
- obj.specobject-type: heading
- ChapterName: 10.4.2 Formula output

##### prov-100000012-b000374d406e47d: Formula output (provision)
- If the source document is an XML instance, the formulas shall be output in the MathML (see 10.4.1) format.
- If character-encoded output is not supported in the target software, all formulas shall be output as graphics (see 10.3.1) to ensure a rendering even.
- bib.al.original-language: en
- bib.dp.publication-date: 2025-03-01
- ids.document: 99200
- ids.element: o1749224057504-sub-10.4.2
- ids.language-synoptic: o1749224057504-sub-10.4.2
- ids.tracing: hash-ca87f73dd3a5d50e3b333fb560e8f892b786f22b774ba745ee724ff9d73836c4
- obj.clause-number: 10.4.2
- obj.element-name: unordered-list
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-c6c195799f914e4
- cross-reference -> prov-100000012-93aea9deeae94ab

##### tr--6d400e6f-d82a-44a1-8922-1185ec080fbf--QLk6r9OVGPxB: Formula output (provision)
All formula variants shall be output as attachments to facilitate re-use of the information.
- bib.al.original-language: en
- bib.dp.publication-date: 2025-03-01
- ids.document: 99200
- ids.element: o1749224057504-sub-10.4.2
- ids.language-synoptic: o1749224057504-sub-10.4.2
- ids.tracing: hash-608380540c88f968d046360b71edc3a0e4be6b347171931c40df3ca2d30256e9
- obj.clause-number: 10.4.2
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### tr--6d400e6f-d82a-44a1-8922-1185ec080fbf--OIeZGlHLQiVA: Formula output (provision)
All formulas shall be output within the XHTML™ 1.0 at the position where they appear in the source text.
- bib.al.original-language: en
- bib.dp.publication-date: 2025-03-01
- ids.document: 99200
- ids.element: o1749224057504-sub-10.4.2
- ids.language-synoptic: o1749224057504-sub-10.4.2
- ids.tracing: hash-1d53a100c179327d980f27fb8e6ae60126eb507f464eed20cc19cd14dc75bba8
- obj.clause-number: 10.4.2
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-66e0bcb81e584b4: Formula output (provision)
EXAMPLE: <THE-VALUE> <xhtml:div> <xhtml:p xml:lang="en"> <xhtml:object data="formulas/42.mml" type="application/mathml-presentation+xml"> <xhtml:object data="formulas/42.png" type="image/png">Formula missing!</xhtml:object> </xhtml:object> </xhtml:p> </xhtml:div> </THE-VALUE>
- bib.al.original-language: en
- bib.dp.publication-date: 2025-03-01
- ids.document: 99200
- ids.element: o1749224057504-sub-10.4.2
- ids.language-synoptic: o1749224057504-sub-10.4.2
- ids.tracing: hash-468fe07b7724de33e764a85787e98f790aae1bce81df109510d32f595141a065
- obj.clause-number: 10.4.2
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

#### prov-100000012-7b80293de4054ca: Dissolve in-line formulas (heading)
- bib.al.original-language: en
- bib.dp.publication-date: 2025-03-01
- ids.document: 99200
- ids.element: o1749224057506-sub-10.4.3
- ids.language-synoptic: o1749224057506-sub-10.4.3
- ids.tracing: hash-c5206acb874b055ab26fb83088074ff6fba029c9792c5d6bbb12c61522c4b032
- obj.clause-number: 10.4.3
- obj.element-name: heading
- obj.language: en
- obj.specobject-type: heading
- ChapterName: 10.4.3 Dissolve in-line formulas

##### tr--6d400e6f-d82a-44a1-8922-1185ec080fbf--NzFIinXh7ylF: Dissolve in-line formulas (provision)
To optimize the machine-processing and reading flow, in-line formulas should be resolved if they:
- can be substituted with text formatting in XHTML™ 1.0.
- do not contain any formula characters that cannot be displayed as XHTML™ 1.0 text.
- bib.al.original-language: en
- bib.dp.publication-date: 2025-03-01
- ids.document: 99200
- ids.element: o1749224057506-sub-10.4.3
- ids.language-synoptic: o1749224057506-sub-10.4.3
- ids.tracing: hash-bcac6609eadda26a972d2abdec8104f09621ec3d83d562ff2631b9ff4c824c3d
- obj.clause-number: 10.4.3
- obj.element-name: paragraph
- obj.language: en
- obj.modality: recommendation
- obj.normativity: normative
- obj.specobject-type: provision
- use.business-process: undefined
- use.business-sector: undefined
- use.interaction: undefined
- use.location: undefined
- use.product-category: undefined
- use.product-life-cycle: undefined
- use.project-phase: undefined
- use.purpose: undefined

##### tr--6d400e6f-d82a-44a1-8922-1185ec080fbf--epgjjBmtEpTl: Dissolve in-line formulas (provision)
Text formatting should be substituted in XHTML™ 1.0:
- fractions, provided they can be represented with a slash (/), i. e. if numerator and denominator are no complex terms and can be represented without additional parenthesis;
- bold (<b>);
- upright (null);
- superscript (<sup>);
- parentheses and posts if trivialisable ({[(|)]});
- italics (<i>);
- small caps font (small caps);
- typewriter font (<tt>);
- font with serifs (<serif>);
- serifless font (<sans-serif>);
- subscript (<sub>).
- bib.al.original-language: en
- bib.dp.publication-date: 2025-03-01
- ids.document: 99200
- ids.element: o1749224057506-sub-10.4.3
- ids.language-synoptic: o1749224057506-sub-10.4.3
- ids.tracing: hash-666566884ba3c79301cb6763632a3b22d0aa1e42dda43c35fbe83da5607bd45c
- obj.clause-number: 10.4.3
- obj.element-name: paragraph
- obj.language: en
- obj.modality: recommendation
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-14fc41cc9e664e2: Dissolve in-line formulas (provision)
EXAMPLE: <xhtml:p xml:lang="en">The Einstein insight is <xhtml:span style="font-family:Cambria Math,Times,serif"><xhtml:i>E</xhtml:i> = <xhtml:i>m</xhtml:i> c<xhtml:sup>2</xhtml:sup><xhtml:span>.</xhtml:p>
- bib.al.original-language: en
- bib.dp.publication-date: 2025-03-01
- ids.document: 99200
- ids.element: o1749224057506-sub-10.4.3
- ids.language-synoptic: o1749224057506-sub-10.4.3
- ids.tracing: hash-b68caa97884203c689e2d66491b9fbee3e845d02fe486374bb742f562f7bff80
- obj.clause-number: 10.4.3
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### prov-100000012-dd81684bc3c743c: Footnotes (heading)
- bib.al.original-language: en
- bib.dp.publication-date: 2025-03-01
- ids.document: 99200
- ids.element: o1749224057508-sub-10.5
- ids.language-synoptic: o1749224057508-sub-10.5
- ids.tracing: hash-9401f45c7765751ff135259a3702b0943c3cd4a3692bf98d0e4a70eabe4ba1e6
- obj.clause-number: 10.5
- obj.element-name: heading
- obj.language: en
- obj.specobject-type: heading
- ChapterName: 10.5 Footnotes

#### tr--6d400e6f-d82a-44a1-8922-1185ec080fbf--pSJP5sSU9q5d: Footnotes (provision)
The content of all footnotes referenced within a SpecObject shall be embedded so that each SpecObject contains the complete information of the referenced footnotes.
- bib.al.original-language: en
- bib.dp.publication-date: 2025-03-01
- ids.document: 99200
- ids.element: o1749224057508-sub-10.5
- ids.language-synoptic: o1749224057508-sub-10.5
- ids.tracing: hash-ae524ddded995d31ef8ae5e25d64a57b411d112e6a0c37f4c7b81544aa4332fd
- obj.clause-number: 10.5
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

#### prov-100000012-da7e7fd377fd404: Footnotes (provision)
- Figure footnotes shall be output at the end of the legend.
- Table footnotes shall be output at the end of the table.
- Text footnotes shall be output as a child SpecObject in which the footnote is referenced.
- bib.al.original-language: en
- bib.dp.publication-date: 2025-03-01
- ids.document: 99200
- ids.element: o1749224057508-sub-10.5
- ids.language-synoptic: o1749224057508-sub-10.5
- ids.tracing: hash-a24317fd350fe95fbefe0c483070580a61a65acce2e880ede0580a1f1f57ea8b
- obj.clause-number: 10.5
- obj.element-name: unordered-list
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

### prov-100000012-080c841430f640f: Tables (heading)
- bib.al.original-language: en
- bib.dp.publication-date: 2025-03-01
- ids.document: 99200
- ids.element: o1749224057511-sub-10.6
- ids.language-synoptic: o1749224057511-sub-10.6
- ids.tracing: hash-f7fe670174e0196ab3035646380e44e76159577197c9a016b784261b5be37e5c
- obj.clause-number: 10.6
- obj.element-name: heading
- obj.language: en
- obj.specobject-type: heading
- ChapterName: 10.6 Tables

#### prov-100000012-89ac655efa7c45c: Table format (heading)
- bib.al.original-language: en
- bib.dp.publication-date: 2025-03-01
- ids.document: 99200
- ids.element: o1749224057513-sub-10.6.1
- ids.language-synoptic: o1749224057513-sub-10.6.1
- ids.tracing: hash-ae8f86e1e4cb3fe997bd6bd5caf14f610072e00d1040aa566c38c07414c31521
- obj.clause-number: 10.6.1
- obj.element-name: heading
- obj.language: en
- obj.specobject-type: heading
- ChapterName: 10.6.1 Table format

##### tr--6d400e6f-d82a-44a1-8922-1185ec080fbf--8YkGv3d1dzKf: Table format (provision)
To ensure rendering in common target software, all table markup shall be output according to the W3C Basic Table Module of the XHTML™ Modularization 1.1.
- bib.al.original-language: en
- bib.dp.publication-date: 2025-03-01
- ids.document: 99200
- ids.element: o1749224057513-sub-10.6.1
- ids.language-synoptic: o1749224057513-sub-10.6.1
- ids.tracing: hash-671c61dba6e4c2772fa0c261bbad700d042772d1fbcc1183b9a15c00b74e3bb8
- obj.clause-number: 10.6.1
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

#### prov-100000012-a3b729ae10534dd: Table output (heading)
- bib.al.original-language: en
- bib.dp.publication-date: 2025-03-01
- ids.document: 99200
- ids.element: o1749224057515-sub-10.6.2
- ids.language-synoptic: o1749224057515-sub-10.6.2
- ids.tracing: hash-30af3ee4efbc43e809e3750ce806f5cb269aa7a6915768a8b9c7590f2e41636e
- obj.clause-number: 10.6.2
- obj.element-name: heading
- obj.language: en
- obj.specobject-type: heading
- ChapterName: 10.6.2 Table output

##### prov-100000012-aecb17198ace4e9: Table output (provision)
- If the source document is an XML instance, the tables shall be output in the HTML table (see 10.6.1) format.
- A table may be output as graphics (see 10.3.1) at the position where it appears in the text, only if it cannot be rendered in the HTML table format without issues relevant for the interpretation of provisions.
- bib.al.original-language: en
- bib.dp.publication-date: 2025-03-01
- ids.document: 99200
- ids.element: o1749224057515-sub-10.6.2
- ids.language-synoptic: o1749224057515-sub-10.6.2
- ids.tracing: hash-28df4109aaea01d14fec4cbdbea3b569896e436f62932fa462eb7ed71e7f7fc6
- obj.clause-number: 10.6.2
- obj.element-name: unordered-list
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-89ac655efa7c45c
- cross-reference -> prov-100000012-93aea9deeae94ab

##### tr--6d400e6f-d82a-44a1-8922-1185ec080fbf--cK9ibMksR3ox: Table output (provision)
All table variants shall be output as attachments to facilitate re-use of the information.
- bib.al.original-language: en
- bib.dp.publication-date: 2025-03-01
- ids.document: 99200
- ids.element: o1749224057515-sub-10.6.2
- ids.language-synoptic: o1749224057515-sub-10.6.2
- ids.tracing: hash-73ce9797708085a5f497147a54e6a870c0186596e7827179f10eef97ab2b188f
- obj.clause-number: 10.6.2
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### tr--6d400e6f-d82a-44a1-8922-1185ec080fbf--DHdEiSwGOQyG: Table output (provision)
All tables shall be output within the XHTML™ 1.0 at the position where they appear in the source text.
- bib.al.original-language: en
- bib.dp.publication-date: 2025-03-01
- ids.document: 99200
- ids.element: o1749224057515-sub-10.6.2
- ids.language-synoptic: o1749224057515-sub-10.6.2
- ids.tracing: hash-867d7e0ccf70f4c80b398403f99a27002f354fb30647ab53e4590daab6bbd5f2
- obj.clause-number: 10.6.2
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

#### prov-100000012-d63d5cda4b7b423: Normalization of tables (heading)
- bib.al.original-language: en
- bib.dp.publication-date: 2025-03-01
- ids.document: 99200
- ids.element: o1749224057517-sub-10.6.3
- ids.language-synoptic: o1749224057517-sub-10.6.3
- ids.tracing: hash-2225af7e02c9574c645cda6ce586b8036d70cbc29b6776c7a4f6700b80943f95
- obj.clause-number: 10.6.3
- obj.element-name: heading
- obj.language: en
- obj.specobject-type: heading
- ChapterName: 10.6.3 Normalization of tables

##### tr--6d400e6f-d82a-44a1-8922-1185ec080fbf--lTretLuo7LVb: Normalization of tables (provision)
The following HTML table markup shall be output so that the tables can be rendered in the target software without issues relevant for the interpretation of provisions:
- column separators;
- horizontal alignment;
- horizontal spans;
- row separators;
- vertical alignment;
- vertical spans.
- bib.al.original-language: en
- bib.dp.publication-date: 2025-03-01
- ids.document: 99200
- ids.element: o1749224057517-sub-10.6.3
- ids.language-synoptic: o1749224057517-sub-10.6.3
- ids.tracing: hash-fd325c3b77a967f6c14e613f6dee14b86abcecdf248d02fd5e55360e4bd4dcd1
- obj.clause-number: 10.6.3
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

## prov-100000012-cedd90735d8a4ba: Digital material to the ReqIF™ interpretation for public standards (heading)
- bib.al.original-language: en
- bib.dp.publication-date: 2025-03-01
- ids.document: 99200
- ids.element: o1749224057520-sub-11
- ids.language-synoptic: o1749224057520-sub-11
- ids.tracing: hash-35276d7d585b2ebfad0d295ec45bfbaf789e04bac9ebfd3be049b2908b246852
- obj.clause-number: 11
- obj.element-name: heading
- obj.language: en
- obj.specobject-type: heading
- ChapterName: 11 Digital material to the ReqIF™ interpretation for public standards

### prov-100000012-17d729caeefe4e1: Benchmarking (heading)
- bib.al.original-language: en
- bib.dp.publication-date: 2025-03-01
- ids.document: 99200
- ids.element: o1749224057522-sub-11.1
- ids.language-synoptic: o1749224057522-sub-11.1
- ids.tracing: hash-b2e0768f7004526c7ddde1166c97b3d7808ac10e1aa62f1269f2e83fe641857b
- obj.clause-number: 11.1
- obj.element-name: heading
- obj.language: en
- obj.specobject-type: heading
- ChapterName: 11.1 Benchmarking

#### tr--6d400e6f-d82a-44a1-8922-1185ec080fbf--N0WKtM21Y1gx: Benchmarking (provision)
To validate the level of conformance to this specification, DIN and DKE provide a test set of ReqIF™ files for publicly available technical rules or publicly available legislative regulations, currently:
- testnorm.reqifz: ReqIF™ file for benchmarking the rendition of the standard elements for technical rules.
- testpublication.reqifz: ReqIF™ file for benchmarking the rendition of the standard elements for secondary content.
- testrequirements.reqifz: ReqIF™ file for benchmarking the pre-classification of attribute with values, the fragmentation of the source document and the recognition of sentences in the source document.
- bib.al.original-language: en
- bib.dp.publication-date: 2025-03-01
- ids.document: 99200
- ids.element: o1749224057522-sub-11.1
- ids.language-synoptic: o1749224057522-sub-11.1
- ids.tracing: hash-f7a26401c1de6f283c2bf48c535edc2365b0563e1129826e36e36bf9f36ee2d0
- obj.clause-number: 11.1
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-100000012-6bf676b31f9c4c1: Examples (heading)
- bib.al.original-language: en
- bib.dp.publication-date: 2025-03-01
- ids.document: 99200
- ids.element: o1749224057524-sub-11.2
- ids.language-synoptic: o1749224057524-sub-11.2
- ids.tracing: hash-8a98f453b1466a58ec556ef347545580cca7898a1c6df5fd37c7c1c4c7c51253
- obj.clause-number: 11.2
- obj.element-name: heading
- obj.language: en
- obj.specobject-type: heading
- ChapterName: 11.2 Examples

#### tr--6d400e6f-d82a-44a1-8922-1185ec080fbf--3YCrVoCpfrGg: Examples (provision)
To facilitate the use of this specification, DIN and DKE provide a test set of ReqIF™ files as examples for publicly available technical rules or publicly available legislative regulations.
- bib.al.original-language: en
- bib.dp.publication-date: 2025-03-01
- ids.document: 99200
- ids.element: o1749224057524-sub-11.2
- ids.language-synoptic: o1749224057524-sub-11.2
- ids.tracing: hash-f134e6051baf31795bee6b6d5b134233dac479501b8a171274c8a21268d7d5d6
- obj.clause-number: 11.2
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-100000012-da658d9b664941f: Tables to the data model (heading)
- bib.al.original-language: en
- bib.dp.publication-date: 2025-03-01
- ids.document: 99200
- ids.element: o1749224057526-sub-11.3
- ids.language-synoptic: o1749224057526-sub-11.3
- ids.tracing: hash-04cb58278d5cd275d5929d1049580430543b40ce7905bf322bb41f42325e6215
- obj.clause-number: 11.3
- obj.element-name: heading
- obj.language: en
- obj.specobject-type: heading
- ChapterName: 11.3 Tables to the data model

#### tr--6d400e6f-d82a-44a1-8922-1185ec080fbf--6e2ZnvgM32E0: Tables to the data model (provision)
To facilitate the use of this specification, the several tables can be obtained as MS® Excel®^ ^3 file from the official web page for this specification, currently:
- user stories for requirements engineering (see Annex A);
- data model (see 8.2 and 8.3);
- long name and identifier syntax (see 8.4);
- class name abbreviations (see 8.5);
- standards for document metadata (see the Metadata Field Specification);
- update flag: actual values and definitions (see the Metadata Field Specification);
- document type: actual values and definitions (see the Metadata Field Specification);
- attribute and content outputs: checklists for implementing 9.2;
- supplementary source information.
- bib.al.original-language: en
- bib.dp.publication-date: 2025-03-01
- ids.document: 99200
- ids.element: o1749224057526-sub-11.3
- ids.language-synoptic: o1749224057526-sub-11.3
- ids.tracing: hash-0f79752c440e4c1e554c5a78d5c58d18141331f64e887ad67d1de93f3a057d58
- obj.clause-number: 11.3
- obj.element-name: paragraph
- obj.language: en
- obj.modality: permission
- obj.normativity: normative
- obj.specobject-type: provision
- obj.transformation-issues: Possibly wrong modal verb
- use.business-process: undefined
- use.business-sector: undefined
- use.interaction: undefined
- use.location: undefined
- use.product-category: undefined
- use.product-life-cycle: undefined
- use.project-phase: undefined
- use.purpose: undefined
- cross-reference -> prov-100000012-cecca7a42e7f463
- cross-reference -> prov-100000012-252f89746a5e4d1
- cross-reference -> prov-100000012-62b877911c1c4ff
- cross-reference -> prov-100000012-e0c5df8513054b8
- cross-reference -> prov-100000012-5397288d2c3b4f7
- cross-reference -> prov-100000012-2cb50e2fc93b465

#### prov-100000012-3e748c80f205436: Tables to the data model, Note (provision)
NOTE:
As added value to the tables in the document, predefined collapsable groups and filters for all columns can be used in the MS® Excel®^ ^3 file.
- bib.al.original-language: en
- bib.dp.publication-date: 2025-03-01
- ids.document: 99200
- ids.element: o1749224057526-sub-11.3
- ids.language-synoptic: o1749224057526-sub-11.3
- ids.tracing: hash-fbba01f6d027a9718b9f628b8929ec13ff487c7a53aa9d0fc37aa65ff833d220
- obj.clause-number: 11.3
- obj.element-name: note
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### prov-100000012-c10980b7dc09486: Utilities for the import and export processes (scripts or templates) (heading)
- bib.al.original-language: en
- bib.dp.publication-date: 2025-03-01
- ids.document: 99200
- ids.element: o1749224057528-sub-11.4
- ids.language-synoptic: o1749224057528-sub-11.4
- ids.tracing: hash-696a78a15768f24b28e6eddbc93a3686b0f1bf921a7f7f9ecd3894d26ff3188f
- obj.clause-number: 11.4
- obj.element-name: heading
- obj.language: en
- obj.specobject-type: heading
- ChapterName: 11.4 Utilities for the import and export processes (scripts or templates)

#### tr--6d400e6f-d82a-44a1-8922-1185ec080fbf--rX4owqITvRcL: Utilities for the import and export processes (scripts or templates) (provision)
If the automatization of the import process shall be improved, the scripts or templates deliverables can be obtained from the official web page for this specification.
- bib.al.original-language: en
- bib.dp.publication-date: 2025-03-01
- ids.document: 99200
- ids.element: o1749224057528-sub-11.4
- ids.language-synoptic: o1749224057528-sub-11.4
- ids.tracing: hash-e352788e2b706dbdae0291eb0d7bcafc9a8ec01d097ab70b9f6075b52fc5d75b
- obj.clause-number: 11.4
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

#### prov-100000012-c66d27218ce14bb: Utilities for the import and export processes (scripts or templates), Note (provision)
NOTE:
If supported by the target software, the use of import or project templates can accelerate or simplify the process by creating the desired sequence of the attributes instead of the common alphabetical default order.
- bib.al.original-language: en
- bib.dp.publication-date: 2025-03-01
- ids.document: 99200
- ids.element: o1749224057528-sub-11.4
- ids.language-synoptic: o1749224057528-sub-11.4
- ids.tracing: hash-3a173d86ba12a4d3470d22e6ca52713badab1d0b2972775e25f2bb4ffe0277f0
- obj.clause-number: 11.4
- obj.element-name: note
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### prov-100000012-518d82a669ff4f2: Validating the data model release 1.3 (Schematron) (heading)
- bib.al.original-language: en
- bib.dp.publication-date: 2025-03-01
- ids.document: 99200
- ids.element: o1749224057530-sub-11.5
- ids.language-synoptic: o1749224057530-sub-11.5
- ids.tracing: hash-8e8eeb8cec267a54449907e006ade910ef7ca780ddcf79edf3c5ae7985780f51
- obj.clause-number: 11.5
- obj.element-name: heading
- obj.language: en
- obj.specobject-type: heading
- ChapterName: 11.5 Validating the data model release 1.3 (Schematron)

#### tr--6d400e6f-d82a-44a1-8922-1185ec080fbf--lPbFqb4dOWNk: Validating the data model release 1.3 (Schematron) (provision)
If a ReqIF™ file shall be validated against this specification, the Schematron deliverables can be obtained from the official web page for this specification.
- bib.al.original-language: en
- bib.dp.publication-date: 2025-03-01
- ids.document: 99200
- ids.element: o1749224057530-sub-11.5
- ids.language-synoptic: o1749224057530-sub-11.5
- ids.tracing: hash-ee9ae2cd9539de2b6bd29dbf71c111dc02046ad8a60ebc497700bd1e1162f8bc
- obj.clause-number: 11.5
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

#### tr--6d400e6f-d82a-44a1-8922-1185ec080fbf--ZimxoL6ON5TA: Validating the data model release 1.3 (Schematron) (provision)
Validating against this specification using this Schematron should not be mixed up with the validation of the ReqIF™ 1.2 format using the corresponding XML Schema Definition.
- bib.al.original-language: en
- bib.dp.publication-date: 2025-03-01
- ids.document: 99200
- ids.element: o1749224057530-sub-11.5
- ids.language-synoptic: o1749224057530-sub-11.5
- ids.tracing: hash-d5ef04c5fd029e2c327dfd5a216f4e95b17e05b8ec275992300b95c1eab953a8
- obj.clause-number: 11.5
- obj.element-name: paragraph
- obj.language: en
- obj.modality: recommendation
- obj.normativity: normative
- obj.specobject-type: provision
- use.business-process: undefined
- use.business-sector: undefined
- use.interaction: undefined
- use.location: undefined
- use.product-category: undefined
- use.product-life-cycle: undefined
- use.project-phase: undefined
- use.purpose: undefined

#### prov-100000012-93d627ba1709406: Validating the data model release 1.3 (Schematron), Note (provision)
NOTE:
For the Schematron specification see ISO/IEC 19757-3.
- bib.al.original-language: en
- bib.dp.publication-date: 2025-03-01
- ids.document: 99200
- ids.element: o1749224057530-sub-11.5
- ids.language-synoptic: o1749224057530-sub-11.5
- ids.tracing: hash-08337de5e50c67611c9c0aeb83cc480a3882a8d40036f53519fee1857ff360a2
- obj.clause-number: 11.5
- obj.element-name: note
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

## prov-100000012-cecca7a42e7f463: User stories for requirements engineering (heading)
- bib.al.original-language: en
- bib.dp.publication-date: 2025-03-01
- ids.document: 99200
- ids.element: o1749224057535-sub-a
- ids.language-synoptic: o1749224057535-sub-a
- ids.tracing: hash-4f9ed368b6d38743f65de030db6b98ce1acbd4ecb9e91f5405bbcf267447e4ee
- obj.clause-number: Annex A
- obj.element-name: heading
- obj.language: en
- obj.specobject-type: heading
- ChapterName: Annex A User stories for requirements engineering

### tr--6d400e6f-d82a-44a1-8922-1185ec080fbf--kUXU5weacsGA: User stories for requirements engineering (provision)
As requirements engineer, I would like to be able to filter SpecObject by metadata.
- bib.al.original-language: en
- bib.dp.publication-date: 2025-03-01
- ids.document: 99200
- ids.element: o1749224057535-sub-a
- ids.language-synoptic: o1749224057535-sub-a
- ids.tracing: hash-7567d0f7196f2bd616fe81f34431552998829d96ee98429a1cc394cac5b24852
- obj.clause-number: Annex A
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### tr--6d400e6f-d82a-44a1-8922-1185ec080fbf--RzIqISLy8XJP: User stories for requirements engineering (provision)
As requirements engineer, I want to be able to search SpecObject for metadata.
- bib.al.original-language: en
- bib.dp.publication-date: 2025-03-01
- ids.document: 99200
- ids.element: o1749224057535-sub-a
- ids.language-synoptic: o1749224057535-sub-a
- ids.tracing: hash-014dfb736bed1fd12d873951949170bdecaeef17292eff703d2814abacd29f08
- obj.clause-number: Annex A
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### tr--6d400e6f-d82a-44a1-8922-1185ec080fbf--4Em68i5j4zMy: User stories for requirements engineering (provision)
As requirements engineer, I want to be able to determine from which document and from which edition the SpecObject originates (source).
- bib.al.original-language: en
- bib.dp.publication-date: 2025-03-01
- ids.document: 99200
- ids.element: o1749224057535-sub-a
- ids.language-synoptic: o1749224057535-sub-a
- ids.tracing: hash-e1a2b4c72aa0977e0ceaa05b1946490cee38fe7f5c54e5ad42154aef1839e39b
- obj.clause-number: Annex A
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### tr--6d400e6f-d82a-44a1-8922-1185ec080fbf--Cp3ix1qfILE8: User stories for requirements engineering (provision)
As requirements engineer, I want to be able to track changes to an actual SpecObject compared to one from previous editions.
- bib.al.original-language: en
- bib.dp.publication-date: 2025-03-01
- ids.document: 99200
- ids.element: o1749224057535-sub-a
- ids.language-synoptic: o1749224057535-sub-a
- ids.tracing: hash-b17b28c8c6ef69cced7dc743b836d09aa2dd90903f69be2e4f080aa31379558c
- obj.clause-number: Annex A
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### tr--6d400e6f-d82a-44a1-8922-1185ec080fbf--DVaiVHSxzGZs: User stories for requirements engineering (provision)
As requirements engineer, I want to be able to trace the impact of amendment documents or correction documents on a SpecObject.
- bib.al.original-language: en
- bib.dp.publication-date: 2025-03-01
- ids.document: 99200
- ids.element: o1749224057535-sub-a
- ids.language-synoptic: o1749224057535-sub-a
- ids.tracing: hash-dd94ff72c14b137e398ea3a0ed91c03366277daf862f40f11b5ea86d0320765b
- obj.clause-number: Annex A
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### tr--6d400e6f-d82a-44a1-8922-1185ec080fbf--YgDvlf1AN7x1: User stories for requirements engineering (provision)
As requirements engineer, I want to be able to find the corresponding SpecObject source for a SpecObject, regardless of where it is located and where it has been moved to (single source of truth).
- bib.al.original-language: en
- bib.dp.publication-date: 2025-03-01
- ids.document: 99200
- ids.element: o1749224057535-sub-a
- ids.language-synoptic: o1749224057535-sub-a
- ids.tracing: hash-83025784d9c5938f4d91407d7f41d738eb050c7dc43ed848f39c83e9200c982b
- obj.clause-number: Annex A
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### tr--6d400e6f-d82a-44a1-8922-1185ec080fbf--oo0GatN23dl0: User stories for requirements engineering (provision)
As requirements engineer, I need the document identifier as an attribute on each SpecObject in order to be able to establish the relationship to the source and its metadata.
- bib.al.original-language: en
- bib.dp.publication-date: 2025-03-01
- ids.document: 99200
- ids.element: o1749224057535-sub-a
- ids.language-synoptic: o1749224057535-sub-a
- ids.tracing: hash-d762de93f1fbc31a3f9803c0065aa1b92b4311b199970a36b27d5ab921c924b7
- obj.clause-number: Annex A
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### tr--6d400e6f-d82a-44a1-8922-1185ec080fbf--xOt4wjtvkMQm: User stories for requirements engineering (provision)
As requirements engineer, I want to be able to jump to the applicable standards.
- bib.al.original-language: en
- bib.dp.publication-date: 2025-03-01
- ids.document: 99200
- ids.element: o1749224057535-sub-a
- ids.language-synoptic: o1749224057535-sub-a
- ids.tracing: hash-60671173d67ef840747fc9e8a8986b4fe4387a1735d6c6dbddfe56b99149205d
- obj.clause-number: Annex A
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

## prov-100000012-89ac3171bcc648d: Background on identifiers (IDs) (heading)
- bib.al.original-language: en
- bib.dp.publication-date: 2025-03-01
- ids.document: 99200
- ids.element: o1749224057538-sub-b
- ids.language-synoptic: o1749224057538-sub-b
- ids.tracing: hash-e22e45329c3ec5279203860c0d3ffb766a21977b48370b5bf3e9b41a1e81584e
- obj.clause-number: Annex B
- obj.element-name: heading
- obj.language: en
- obj.specobject-type: heading
- ChapterName: Annex B Background on identifiers (IDs)

### prov-100000012-cbe73fe9fbcd49b: User Stories for identifiers (IDs) (heading)
- bib.al.original-language: en
- bib.dp.publication-date: 2025-03-01
- ids.document: 99200
- ids.element: o1749224057540-sub-b.1
- ids.language-synoptic: o1749224057540-sub-b.1
- ids.tracing: hash-cbd2b7748b2ee7a8841a47682d47f450fc2e2a1433a1bab5eacbf450af58304e
- obj.clause-number: B.1
- obj.element-name: heading
- obj.language: en
- obj.specobject-type: heading
- ChapterName: B.1 User Stories for identifiers (IDs)

#### prov-100000012-ee136d0eea4e400: User Stories for identifiers (IDs) (provision)
- As user of a SpecObject I want to identify documents uniquely using machine-resolvable database keys (document IDs).
- As user of a SpecObject I want to be able to link to fragments within target documents, using speaking identifiers (IDs) based on the references within the source document (element IDs).
- As user of a SpecObject I want to identify synoptic elements in different language variants for the same version of the same document (language-independent IDs).
- As user of a SpecObject I want to identify fragments uniquely by using path and offset independently or below the element contexts given in the content (path IDs).
- As user of a SpecObject I want to make fragments unambiguously traceable across the versions of the same context (version-independent tracing IDs).
- As user of a SpecObject I want to identify fragments uniquely, using globally (GUID), universally (UUID) or other unique identifiers (version-independent unique IDs).
- bib.al.original-language: en
- bib.dp.publication-date: 2025-03-01
- ids.document: 99200
- ids.element: o1749224057540-sub-b.1
- ids.language-synoptic: o1749224057540-sub-b.1
- ids.tracing: hash-98ce64a7d4fd113bc0b086a7cd2d7594ac7457cce1226bd00d615a321871123b
- obj.clause-number: B.1
- obj.element-name: unordered-list
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### prov-100000012-a14854c2b52c4a6: Initial situation for ID systems (heading)
- bib.al.original-language: en
- bib.dp.publication-date: 2025-03-01
- ids.document: 99200
- ids.element: o1749224057542-sub-b.2
- ids.language-synoptic: o1749224057542-sub-b.2
- ids.tracing: hash-18e408461ddbad243a7a3d1d7fc8c184e58b456af6138e62825c6f35f1c83981
- obj.clause-number: B.2
- obj.element-name: heading
- obj.language: en
- obj.specobject-type: heading
- ChapterName: B.2 Initial situation for ID systems

#### prov-100000012-9b030d36c836433: Initial situation for ID systems (provision)
- ID systems are already established for some requirements, but not for others.
- Some ID systems are already included throughout the content, for example document IDs and element IDs.
- Some ID systems cannot be provided in the content, i. e. some ID systems shall be located outside the content, for example using RDF.
- Since some requirements are incompatible, no ID system can cover all requirements, so that several ID systems shall be supplied.
- bib.al.original-language: en
- bib.dp.publication-date: 2025-03-01
- ids.document: 99200
- ids.element: o1749224057542-sub-b.2
- ids.language-synoptic: o1749224057542-sub-b.2
- ids.tracing: hash-ae27f30cccb4808c2b489f00a0153c75955664a9f95d56467e268ef43285ee24
- obj.clause-number: B.2
- obj.element-name: unordered-list
- obj.language: en
- obj.modality: requirement
- obj.normativity: informative
- obj.specobject-type: provision
- use.business-process: undefined
- use.business-sector: undefined
- use.interaction: undefined
- use.location: undefined
- use.product-category: undefined
- use.product-life-cycle: undefined
- use.project-phase: undefined
- use.purpose: undefined

### prov-100000012-c97e83c03b23453: Challenges regarding multiple ID systems (heading)
- bib.al.original-language: en
- bib.dp.publication-date: 2025-03-01
- ids.document: 99200
- ids.element: o1749224057544-sub-b.3
- ids.language-synoptic: o1749224057544-sub-b.3
- ids.tracing: hash-a838282f56186882db2a153fe2da6511b3587af9d47a1df52f2fbebea39c2d5a
- obj.clause-number: B.3
- obj.element-name: heading
- obj.language: en
- obj.specobject-type: heading
- ChapterName: B.3 Challenges regarding multiple ID systems

#### prov-100000012-c4035b962bf2446: Challenges regarding multiple ID systems (provision)
- The involved partners should only operate as many ID systems as are minimally necessary so that the processes remain manageable.
- The involved partners should not discard already established ID systems if this would jeopardize the operation of ongoing processes.
- bib.al.original-language: en
- bib.dp.publication-date: 2025-03-01
- ids.document: 99200
- ids.element: o1749224057544-sub-b.3
- ids.language-synoptic: o1749224057544-sub-b.3
- ids.tracing: hash-7b4fe367a5897288fee781f7bc569165c58b1e048b946ddad0e1b5c4811d7b14
- obj.clause-number: B.3
- obj.element-name: unordered-list
- obj.language: en
- obj.modality: recommendation
- obj.normativity: informative
- obj.specobject-type: provision
- use.business-process: undefined
- use.business-sector: undefined
- use.interaction: undefined
- use.location: undefined
- use.product-category: undefined
- use.product-life-cycle: undefined
- use.project-phase: undefined
- use.purpose: undefined

### prov-100000012-bb4f1a38e8c9441: Recommendations for maintaining multiple ID systems (heading)
- bib.al.original-language: en
- bib.dp.publication-date: 2025-03-01
- ids.document: 99200
- ids.element: o1749224057546-sub-b.4
- ids.language-synoptic: o1749224057546-sub-b.4
- ids.tracing: hash-2c9a78b3b133ba54ed79fd2b8bb7692d72adc397334d3f83e774231718f4f75c
- obj.clause-number: B.4
- obj.element-name: heading
- obj.language: en
- obj.specobject-type: heading
- ChapterName: B.4 Recommendations for maintaining multiple ID systems

#### prov-100000012-d88fdb7e8b3e40d: Recommendations for maintaining multiple ID systems (provision)
- The involved partners should identify and minimize redundant ID systems, provided this does not jeopardize the operation of ongoing processes.
- The involved partners should identify and harmonize incompatible ID systems, provided this does not jeopardize the operation of ongoing processes.
- bib.al.original-language: en
- bib.dp.publication-date: 2025-03-01
- ids.document: 99200
- ids.element: o1749224057546-sub-b.4
- ids.language-synoptic: o1749224057546-sub-b.4
- ids.tracing: hash-ec3ddad8e367bbb26370c80ca248d62a139124923cf4503a3e55bb9fd6062d39
- obj.clause-number: B.4
- obj.element-name: unordered-list
- obj.language: en
- obj.modality: recommendation
- obj.normativity: informative
- obj.specobject-type: provision
- use.business-process: undefined
- use.business-sector: undefined
- use.interaction: undefined
- use.location: undefined
- use.product-category: undefined
- use.product-life-cycle: undefined
- use.project-phase: undefined
- use.purpose: undefined

## prov-100000012-823427921a7e4c8: Determination of the normativity (obj.normativity) (heading)
- bib.al.original-language: en
- bib.dp.publication-date: 2025-03-01
- ids.document: 99200
- ids.element: o1749224057548-sub-c
- ids.language-synoptic: o1749224057548-sub-c
- ids.tracing: hash-65e4e8b6f8f75c54ea38592ab94fe5cf97008f216727af8025bbb0edfb93e1cb
- obj.clause-number: Annex C
- obj.element-name: heading
- obj.language: en
- obj.specobject-type: heading
- ChapterName: Annex C Determination of the normativity (obj.normativity)

### tr--6d400e6f-d82a-44a1-8922-1185ec080fbf--E8q4EjkEouqZ: Determination of the normativity (obj.normativity) (provision)
If the source document is an XML instance, the value of the attribute obj.normativity (8.2.1.2) can be determined as follows:
- bib.al.original-language: en
- bib.dp.publication-date: 2025-03-01
- ids.document: 99200
- ids.element: o1749224057548-sub-c
- ids.language-synoptic: o1749224057548-sub-c
- ids.tracing: hash-de0bcafca2fc030aaba683f6972ac9f488528bb2bdf7cf9a0406cd8cd90a1a12
- obj.clause-number: Annex C
- obj.element-name: paragraph
- obj.language: en
- obj.modality: permission
- obj.normativity: normative
- obj.specobject-type: provision
- obj.transformation-issues: Possibly wrong modal verb
- use.business-process: undefined
- use.business-sector: undefined
- use.interaction: undefined
- use.location: undefined
- use.product-category: undefined
- use.product-life-cycle: undefined
- use.project-phase: undefined
- use.purpose: undefined
- cross-reference -> prov-100000012-2f90c5903f8d49c

### prov-100000012-8debf94d3db749a: Determination of the normativity (obj.normativity) (provision)
| informative context | normative context |
| --- | --- |
| The value is “informative” if the context of the current element is: - bibliographic annex; - informative appendix; - example; - footnote; - note; - preface; - introduction; - metadata; profile data (title page); - any other verified informative context. | The value is “normative” if the context of the current element is not an informative context. |
- bib.al.original-language: en
- bib.dp.publication-date: 2025-03-01
- ids.document: 99200
- ids.element: o1749224057548-sub-c
- ids.language-synoptic: o1749224057548-sub-c
- ids.tracing: hash-4cc9682d9fc96b4648e42da694e693cf857834a2725156bbb6337cf03d08a221
- obj.clause-number: Annex C
- obj.element-name: tabular-form
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### tr--6d400e6f-d82a-44a1-8922-1185ec080fbf--bAvMFcOyNMpn: Determination of the normativity (obj.normativity) (provision)
The suppliers should optimize the implemented method during their continuous improvement process.
- bib.al.original-language: en
- bib.dp.publication-date: 2025-03-01
- ids.document: 99200
- ids.element: o1749224057548-sub-c
- ids.language-synoptic: o1749224057548-sub-c
- ids.tracing: hash-dfcab617c2f834e6a7cdc760e0b420ff5832708e9480644fee240c7c369c085d
- obj.clause-number: Annex C
- obj.element-name: paragraph
- obj.language: en
- obj.modality: recommendation
- obj.normativity: normative
- obj.specobject-type: provision
- use.business-process: undefined
- use.business-sector: undefined
- use.interaction: undefined
- use.location: undefined
- use.product-category: undefined
- use.product-life-cycle: undefined
- use.project-phase: undefined
- use.purpose: undefined

### prov-100000012-9a6e792c0021485: Determination of the normativity (obj.normativity), Note (provision)
NOTE:
This method has the advantage, that in case of a mismatch the risk is lower to review a false-classified normative content instead of missing a normative content.
- bib.al.original-language: en
- bib.dp.publication-date: 2025-03-01
- ids.document: 99200
- ids.element: o1749224057548-sub-c
- ids.language-synoptic: o1749224057548-sub-c
- ids.tracing: hash-74df4740985c2b84ac59a5249b1f5403c640f449b620087495d722a4c29631b3
- obj.clause-number: Annex C
- obj.element-name: note
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

## prov-100000012-c726f394be984a9: Determination of the conversion reliability (obj.conversion-reliability) (heading)
- bib.al.original-language: en
- bib.dp.publication-date: 2025-03-01
- ids.document: 99200
- ids.element: o1749224057550-sub-d
- ids.language-synoptic: o1749224057550-sub-d
- ids.tracing: hash-f5027f6e42066f9b206fd5db685213caca09fa7bd0539a7e9d5c1946fb1d5bf4
- obj.clause-number: Annex D
- obj.element-name: heading
- obj.language: en
- obj.specobject-type: heading
- ChapterName: Annex D Determination of the conversion reliability (obj.conversion-reliability)

### tr--6d400e6f-d82a-44a1-8922-1185ec080fbf--IcpbQtF573k6: Determination of the conversion reliability (obj.conversion-reliability) (provision)
If the source document is an XML instance, the value of the attribute obj.conversion-reliability (8.2.1.2) can be determined the occurrences of:
- words in a sentence;
- “and”;
- “not”;
- “or”;
- “shall” and “have to” (requirement);
- “should” and “ought” (recommendation);
- “may” and “can” (capability or possibility);
- “must” (external constraint);
- “is” or “are”;
- “de:soll” or “de:sollen” (ambiguous and therefore deprecated);
- infinitives, for example “to carry out” or “to check”;
- “accordingly”, “or”, or “respectively”;
- “for example”, “e. g.”, or “e.g.”;
- “and so forth”, “and so on”, “et cetera”, or “etc.”.
- bib.al.original-language: en
- bib.dp.publication-date: 2025-03-01
- ids.document: 99200
- ids.element: o1749224057550-sub-d
- ids.language-synoptic: o1749224057550-sub-d
- ids.tracing: hash-a8774aad66a93a4ca7a387f6ca8ca8f6febf465e6c90a917e741b2e09b8b47b6
- obj.clause-number: Annex D
- obj.element-name: paragraph
- obj.language: en
- obj.modality: permission
- obj.normativity: informative
- obj.specobject-type: provision
- obj.transformation-issues: Possibly wrong modal verb
- use.business-process: undefined
- use.business-sector: undefined
- use.interaction: undefined
- use.location: undefined
- use.product-category: undefined
- use.product-life-cycle: undefined
- use.project-phase: undefined
- use.purpose: undefined
- cross-reference -> prov-100000012-2f90c5903f8d49c

### tr--6d400e6f-d82a-44a1-8922-1185ec080fbf--kbzw8D1lA10g: Determination of the conversion reliability (obj.conversion-reliability) (provision)
The suppliers should optimize the implemented method during their continuous improvement process.
- bib.al.original-language: en
- bib.dp.publication-date: 2025-03-01
- ids.document: 99200
- ids.element: o1749224057550-sub-d
- ids.language-synoptic: o1749224057550-sub-d
- ids.tracing: hash-f8ee51b76f9f19de1c687c9b0bac3444af2aa41fd66a6f7f03fb0dcdda9d32da
- obj.clause-number: Annex D
- obj.element-name: paragraph
- obj.language: en
- obj.modality: recommendation
- obj.normativity: informative
- obj.specobject-type: provision
- use.business-process: undefined
- use.business-sector: undefined
- use.interaction: undefined
- use.location: undefined
- use.product-category: undefined
- use.product-life-cycle: undefined
- use.project-phase: undefined
- use.purpose: undefined

## prov-100000012-e5938a2949ed44d: Bibliography (heading)
- bib.al.original-language: en
- bib.dp.publication-date: 2025-03-01
- ids.document: 99200
- ids.element: o1749224057552-sub-annex.bibliography.nat
- ids.tracing: hash-b80cd9eaabbdcd73df73565b2c9f042ce76894fe5c45700e4f13de1832af74e8
- obj.element-name: heading
- obj.language: en
- obj.specobject-type: heading

### prov-100000012-402e6ac107ee49d: Bibliography (provision)
- 1
ISO/IEC 9834-8:2014, Information technology – Procedures for the operation of object identifier registration authorities – Part 8: Generation of universally unique identifiers (UUIDs) and their use in object identifiers
- 2
ISO/IEC 10646, Information technology – Universal coded character set (UCS)
- 3
ISO 12639, Graphic technology – Prepress digital data exchange – Tag image file format for image technology (TIFF/IT)
- 4
ISO/IEC 15948, Information technology – Computer graphics and image processing – Portable Network Graphics (PNG): Functional specification
- 5
ISO/IEC 19757-3, Information technology – Document Schema Definition Languages (DSDL) – Part 3: Rule-based validation using Schematron
- 6
ISO/IEC Guide 2, Standardization and related activities – General vocabulary
- 7
Scenarios for Digitizing Standardization and Standards – Whitepaper 1. IDiS Initiative for Digital Standards (DIN, DKE): Berlin, Offenbach, 2021-06
- 8
Use Cases for SMART Standards – Whitepaper 2. IDiS Initiative for Digital Standards (DIN, DKE): Berlin, Offenbach, 2022-05
- 9
Porter, Michael E. Competitive Advantage: Creating and Sustaining Superior Performance. California: Free Press, 1985.
- 10
A Universally Unique IDentifier (UUID) URN Namespace. Network Working Group, 2005-07. Internet: https://datatracker.ietf.org/doc/html/rfc4122/
- 11
Memorandum of Understanding Between W3C and WHATWG. W3C, 2019-05-28. Internet: https://www.w3.org/2019/04/WHATWG-W3C-MOU.html
- bib.al.original-language: en
- bib.dp.publication-date: 2025-03-01
- ids.document: 99200
- ids.element: o1749224057552-sub-annex.bibliography.nat
- ids.tracing: hash-0ac442a42e017667d462f873ed67e241d0de70bf875d495b5235edbca966a875
- obj.element-name: list-of-documents
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
